submodule openconfig-aft-state-synced {
  // Generated by yanger -t ncs
  tailf:mount-id "oc-all-nc-1.0:oc-all-nc-1.0";

  belongs-to openconfig-aft {
    prefix oc-aft;
  }

  import openconfig-extensions {
    prefix oc-ext;
  }
  import tailf-common {
    prefix tailf;
  }
  import tailf-ncs {
    prefix ncs;
  }

  organization
    "OpenConfig working group";
  contact
    "OpenConfig working group
     www.openconfig.net";
  description
    "Submodule containing definitions of groupings for the state
     synced signals corresponding to various abstract forwarding tables.";
  oc-ext:openconfig-version "2.2.0";

  revision 2022-06-16 {
    description
      "Add state-synced container under afts.";
    reference "2.2.0";
  }

  grouping ncs_template_aft-state-synced-structural {
    description
      "Structural grouping defining the schema for the state synced signals
       of various abstract forwarding table.";
    // NCS drop config false container state
  }

  grouping ncs_rpc_notif_aft-state-synced-structural {
    description
      "Structural grouping defining the schema for the state synced signals
       of various abstract forwarding table.";
    container state {
      config false;
      description
        "Operational state parameters relating to the state
         synced signals of various AFTs.";
      leaf ipv4-unicast {
        type boolean;
        default "false";
        description
          "State synced signal indicating consistent device snapshot of
           IPv4 unicast AFT entries. Before setting this flag to true
           next-hop-groups and next-hops AFT entries, associated with
           ipv4-unicast AFT entries, are expected to be consistent with
           device snapshot.";
      }
      leaf ipv6-unicast {
        type boolean;
        default "false";
        description
          "State synced signal indicating consistent device snapshot of
           IPv6 unicast AFT entries. Before setting this flag to true
           next-hop-groups and next-hops AFT entries, associated with
           ipv6-unicast AFT entries, are expected to be consistent with
           device snapshot.";
      }
    }
  }

  grouping live_ncs_aft-state-synced-structural {
    description
      "Structural grouping defining the schema for the state synced signals
       of various abstract forwarding table.";
    container state {
      description
        "Operational state parameters relating to the state
         synced signals of various AFTs.";
      leaf ipv4-unicast {
        type boolean;
        // NCS drop default statement
        description
          "State synced signal indicating consistent device snapshot of
           IPv4 unicast AFT entries. Before setting this flag to true
           next-hop-groups and next-hops AFT entries, associated with
           ipv4-unicast AFT entries, are expected to be consistent with
           device snapshot.";
      }
      leaf ipv6-unicast {
        type boolean;
        // NCS drop default statement
        description
          "State synced signal indicating consistent device snapshot of
           IPv6 unicast AFT entries. Before setting this flag to true
           next-hop-groups and next-hops AFT entries, associated with
           ipv6-unicast AFT entries, are expected to be consistent with
           device snapshot.";
      }
    }
  }

  grouping aft-state-synced-structural {
    description
      "Structural grouping defining the schema for the state synced signals
       of various abstract forwarding table.";
    // NCS drop config false container state
  }
}
