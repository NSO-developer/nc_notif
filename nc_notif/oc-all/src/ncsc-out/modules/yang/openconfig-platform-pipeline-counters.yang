module openconfig-platform-pipeline-counters {
  // Generated by yanger -t ncs
  tailf:mount-id "oc-all-nc-1.0:oc-all-nc-1.0";
  tailf:ncs-device-type "netconf";

  yang-version 1;
  namespace "http://openconfig.net/yang/platform-pipeline-counters";
  prefix oc-ppc;

  import openconfig-yang-types {
    prefix oc-yang;
  }
  import openconfig-types {
    prefix oc-types;
  }
  import openconfig-extensions {
    prefix oc-ext;
  }
  import openconfig-platform {
    prefix oc-platform;
  }
  import tailf-common {
    prefix tailf;
  }
  import tailf-ncs {
    prefix ncs;
  }

  organization
    "OpenConfig working group";
  contact
    "OpenConfig working group
     www.openconfig.net";
  description
    "Provide fine grain, per-Integrated Circuit (IC), telemetry data streams
     that will identify the health, any packet drops, and any errors on the IC.
     With this additional telemetry, the health of the IC, packet drops and
     errors, can be explicitly monitored not only on a specific router, but also
     on a specific IC on a specific router. The IC is divided into 5 platform
     independent sub-blocks.
      1. IC Interface Subsystem
      2. Queueing Subsystem
      3. Lookup Subsystem
      4. Host Interface
      5. Fabric Interface.
     +++++++++++++++++++++++++++++++++++++++++++++++++++++++++++++++++++++
     |                                                                   |
     | +---------------------------------------------------------------+ |
     | | Integrated +---------------------------------------+          | |
     | | Circuit    |     Host Interface                    |          | |
     | |            +---------------------------------------+          | |
     | |               +------------+                                  | |
     | | +-----------+ |  Lookup    |                  +-------------+ | |
     | | | IC        | |  Subsystem |                  |  Fabric     | | |
     | | | Interface | |            |                  | Interface   | | |
     | | | Subsystem | +------------+                  |             | | |
     | | +-----------+                +-------------+  +-------------+ | |
     | |                              | Queueing    |                  | |
     | |                              | Subsystem   |                  | |
     | |                              +-------------+                  | |
     | |                                                               | |
     | +---------------------------------------------------------------+ |
     |                                                                   |
     +-------------------------------------------------------------------+
     Each IC implementation inside forwarding engines may have a different set of
     counters. Some counters have different names but the same
     functionality and can be grouped together. Most counters are different
     between IC families and will have to be aggregated as generic counters. The
     aggregation could mean either a specific IC counter needs to be mapped to
     one of the values specified in this model, or it may require multiple IC
     counters aggregated to produce one of the values in this model.
     The following classes of counters will generalize the types of
     statistics that are provided from each of the above 5 blocks.
      A. Packet Counters
      B. Drop Counters
      C. Error Counters
     The advantage of grouping all the packet counters for all 5 blocks,
     all drop counters from all 5 blocks, and all error counters from all
     5 blocks, is to have the abililty to receive all drop counters from
     all 5 blocks, for example, with one request.";
  oc-ext:openconfig-version "0.2.1";
  oc-ext:catalog-organization "openconfig";
  oc-ext:origin "openconfig";

  revision 2022-01-19 {
    description
      "Fixed typo for aggregate field.";
    reference "0.2.1";
  }
  revision 2021-10-16 {
    description
      "Update pipeline error counters to allow for multiple errors
       per block.";
    reference "0.2.0";
  }
  revision 2020-07-31 {
    description
      "Initial revision of platform pipeline counters.";
    reference "0.1.0";
  }

  grouping ncs_template_platform-pipeline-top {
    description
      "Top-level structural grouping for platform pipeline
       counters.";
    // NCS drop config false container 'pipeline-counters'
  }

  grouping ncs_template_pipeline-packets-common {
    description
      "A common set of packet counters that apply to multiple packet sections.";
    leaf in-packets {
      type oc-yang:ncs_template_counter64;
      description
        "Incoming packets towards the integrated-circuit interface
         subsystem block from the line interfaces or fabric.";
    }
    leaf out-packets {
      type oc-yang:ncs_template_counter64;
      description
        "Outgoing packets towards the line interfaces or fabric from the
         integrated-circuit interface subsystem block.";
    }
    leaf in-bytes {
      type oc-yang:ncs_template_counter64;
      description
        "Incoming bytes towards the integrated-circuit interface
         subsystem block from the line interfaces or fabric.";
    }
    leaf out-bytes {
      type oc-yang:ncs_template_counter64;
      description
        "Outgoing bytes towards the line interfaces or fabric from the
         integrated-circuit interface subsystem block.";
    }
  }

  grouping ncs_template_pipeline-counters-common-high-low-packets {
    description
      "A common set of high and low priority packet counters that apply to
       multiple packet sections.";
    leaf in-high-priority-packets {
      type oc-yang:ncs_template_counter64;
      description
        "Incoming high priority packets towards the integrated-circuit
         fabric subsystem block from the previous NPU sub block.";
    }
    leaf out-high-priority-packets {
      type oc-yang:ncs_template_counter64;
      description
        "Outgoing high priority packets towards the fabric from the
         integrated-circuit fabric subsystem block.";
    }
    leaf in-low-priority-packets {
      type oc-yang:ncs_template_counter64;
      description
        "Incoming low priority packets towards the integrated-circuit fabric
         subsystem block from the previous NPU sub block.";
    }
    leaf out-low-priority-packets {
      type oc-yang:ncs_template_counter64;
      description
        "Outgoing low priority packets towards the fabric from the
         integrated-circuit fabric subsystem block.";
    }
  }

  grouping ncs_template_pipeline-counters-packet-interface-block-state {
    description
      "Each counter will aggregate incoming and outgoing packets and bytes
       that connect the IC to the external MAC or PHY.";
    uses ncs_template_pipeline-packets-common;
  }

  grouping ncs_template_pipeline-counters-packet-lookup-block-state {
    description
      "The IC lookup subsystem counters include total packets/bytes in/out of
       the lookup subsystem and performance metrics for key functionality of this
       subsystem such as lookup memory usage, nexthop memory usage, ACL,
       and firewall usage";
    leaf lookup-utilization {
      type oc-types:ncs_template_percentage;
      description
        "The integrated-circuit lookup subsystem block utilization percentage.";
    }
    uses ncs_template_pipeline-packets-common;
    leaf lookup-memory {
      type string;
      units "bytes";
      description
        "The total amount of memory available in the lookup subsystem.";
    }
    leaf lookup-memory-used {
      type string;
      units "bytes";
      description
        "The amount of memory used in the lookup subsystem.";
    }
    leaf nexthop-memory {
      type string;
      units "bytes";
      description
        "The total amount of nexthop memory available in the lookup subsystem.";
    }
    leaf nexthop-memory-used {
      type string;
      units "bytes";
      description
        "The amount of nexthops memory used in the lookup subsystem.";
    }
    leaf acl-memory-total-entries {
      type string;
      description
        "Total firewall or ACL memory counter measured in entries.";
    }
    leaf acl-memory-used-entries {
      type string;
      description
        "Amount of used firewall or ACL memory counter measured in entries.
         The number of used entries must include the entries
         that are 'allocated but free' if the memory reaping algorithm makes
         these entries practically unusable.";
    }
    leaf acl-memory-total-bytes {
      type string;
      units "bytes";
      description
        "Total firewall or ACL memory counter measured in bytes.";
    }
    leaf acl-memory-used-bytes {
      type string;
      units "bytes";
      description
        "Amount of used firewall or ACL memory counter measured in bytes.
         The number of used bytes must include the bytes
         that are 'allocated but free' if the memory reaping algorithm makes
         these bytes practically unusable";
    }
    leaf fragment-total-pkts {
      type oc-yang:ncs_template_counter64;
      description
        "Total number of fragments generated by the CPU.";
    }
  }

  grouping ncs_template_pipeline-counters-packet-queueing-block-state {
    description
      "The IC queueing subsystem counters include packets/bytes in/out of the
       queueing subsystem and performance metrics for key functionality of this
       subsystem such as memory used and loopback counts.";
    uses ncs_template_pipeline-packets-common;
    leaf queue-memory {
      type string;
      units "bytes";
      description
        "The total amount of memory available in the queue subsystem.";
    }
    leaf queue-memory-used {
      type string;
      units "bytes";
      description
        "The amount of memory used in the queue subsystem.";
    }
    leaf loopback-packets {
      type oc-yang:ncs_template_counter64;
      description
        "The number of packets in the loopback or re-circulate subsystem.";
    }
    leaf loopback-bytes {
      type string;
      units "bytes";
      description
        "The number of bytes in the loopback or re-circulate subsystem.";
    }
  }

  grouping ncs_template_pipeline-counters-packet-fabric-block-state {
    description
      "The IC fabric subsystem counters include packets/cells in/out of the
       fabric subsystem and performance metrics for key functionality of this
       subsystem such as high and low priority packet counts.";
    leaf in-cells {
      type oc-yang:ncs_template_counter64;
      description
        "Incoming cells towards the integrated-circuit fabric
         subsystem block from the previous NPU sub block.";
    }
    leaf out-cells {
      type oc-yang:ncs_template_counter64;
      description
        "Outgoing cells towards the fabric from the
         integrated-circuit fabric subsystem block.";
    }
    uses ncs_template_pipeline-packets-common;
    leaf in-high-priority-cells {
      type oc-yang:ncs_template_counter64;
      description
        "Incoming high priority cells towards the integrated-circuit fabric
         subsystem block from the previous NPU sub block.";
    }
    leaf out-high-priority-cells {
      type oc-yang:ncs_template_counter64;
      description
        "Outgoing high priority cells towards the fabric from the
         integrated-circuit fabric subsystem block.";
    }
    leaf in-low-priority-cells {
      type oc-yang:ncs_template_counter64;
      description
        "Incoming low priority cells towards the integrated-circuit fabric
         subsystem block from the previous NPU sub block.";
    }
    leaf out-low-priority-cells {
      type oc-yang:ncs_template_counter64;
      description
        "Outgoing low priority cells towards the fabric from the
         integrated-circuit fabric subsystem block.";
    }
    uses ncs_template_pipeline-counters-common-high-low-packets;
  }

  grouping ncs_template_pipeline-counters-packet-host-interface-block-state {
    description
      "The IC host interface counters include packets/bytes in/out of the
       host interface subsystem and performance metrics for key functionality
       of this subsystem such as fragmented packet counts and hi/low priority
       packet counts";
    uses ncs_template_pipeline-packets-common;
    leaf fragment-punt-pkts {
      type oc-yang:ncs_template_counter64;
      description
        "The packets that were successfully punted to CPU due to egress MTU
         exceeded.";
    }
    uses ncs_template_pipeline-counters-common-high-low-packets;
  }

  grouping ncs_template_pipeline-drops-common {
    description
      "A common set of drop counters that apply to multiple drop sections.";
    leaf oversubscription {
      type oc-yang:ncs_template_counter64;
      description
        "Number of packets dropped due to oversubscription of the
         integrated-circuit subsystem block.";
    }
  }

  grouping ncs_template_pipeline-drops-common-high-low {
    description
      "A common set of drop counters for high and low priority.";
    leaf in-high-priority {
      type oc-yang:ncs_template_counter64;
      description
        "Incoming high priority drops towards this integrated-circuit
         subsystem block from the previous NPU sub-block or interface.";
    }
    leaf out-high-priority {
      type oc-yang:ncs_template_counter64;
      description
        "Outgoing high priority drops towards the fabric/interface from this
         integrated-circuit subsystem block.";
    }
    leaf in-low-priority {
      type oc-yang:ncs_template_counter64;
      description
        "Incoming low priority drops towards this integrated-circuit
         subsystem block from the previous NPU sub-block or interface.";
    }
    leaf out-low-priority {
      type oc-yang:ncs_template_counter64;
      description
        "Outgoing low priority drops towards the fabric/interface from this
         integrated-circuit subsystem block.";
    }
  }

  grouping ncs_template_pipeline-drop-packet-interface-block-state {
    description
      "Each drop counter will aggregate incoming and outgoing packets, and
       oversubscription drops that connect the IC to the external MAC or PHY.";
    uses ncs_template_pipeline-drops-common;
    leaf in-drops {
      type oc-yang:ncs_template_counter64;
      description
        "Incoming drops towards the integrated-circuit interface
         subsystem block from the interfaces due to any reason.";
    }
    leaf out-drops {
      type oc-yang:ncs_template_counter64;
      description
        "Outgoing drops towards the interfaces from the
         integrated-circuit interface subsystem block due to any reason.";
    }
  }

  grouping ncs_template_pipeline-drop-packet-lookup-block-state {
    description
      "The IC lookup subsystem drop counters track key functionality of this
       subsystem such as Oversubscription, no-route, no-label, no-NH, invalid-
       packets, forwarding-policy, incorrect-software, rate-limit, fragments,
       and firewall drops";
    uses ncs_template_pipeline-drops-common;
    leaf no-route {
      type oc-yang:ncs_template_counter64;
      description
        "Packets dropped due to no FIB entry for this ipv4 or ipv6 lookup.";
    }
    leaf no-label {
      type oc-yang:ncs_template_counter64;
      description
        "Packets dropped due to no FIB entry for this MPLS label.";
    }
    leaf no-nexthop {
      type oc-yang:ncs_template_counter64;
      description
        "Packets dropped due to no nexthop information - either the nexthop is
         not programmed, or there is an invalid nexthop, or there is no ARP
         information so the nexthop is in invalid state.";
    }
    leaf invalid-packet {
      type oc-yang:ncs_template_counter64;
      description
        "Packets dropped due to invalid packet format for ipv4, ipv6, or MPLS.";
    }
    leaf forwarding-policy {
      type oc-yang:ncs_template_counter64;
      description
        "Packets dropped due to either a filter applied as part of a forwarding
         policy or dropped due to a policy-based-routing policy lookup.";
    }
    leaf incorrect-software-state {
      type oc-yang:ncs_template_counter64;
      description
        "Packets dropped due to any incorrect or invalid software state of the
         forwarding structures during lookup.";
    }
    leaf rate-limit {
      type oc-yang:ncs_template_counter64;
      description
        "Packets dropped due to rate limiters - either user configured rate
         limiters or system rate limiters in the forwarding path.";
    }
    leaf fragment-total-drops {
      type oc-yang:ncs_template_counter64;
      description
        "Total number of packets dropped that could not be fragmented by NPU
         due to DF bit.";
    }
    leaf lookup-aggregate {
      type oc-yang:ncs_template_counter64;
      description
        "Packets dropped due to aggregate lookup drop counters - this counter
         is sometimes referred to as Normal Discards or
         ENQ_DISCARDED_PACKET_COUNTER.";
    }
    leaf acl-drops {
      type oc-yang:ncs_template_counter64;
      description
        "Packets dropped due to firewall or acl terms.";
    }
  }

  grouping ncs_template_pipeline-drop-packet-queueing-block-state {
    description
      "The IC queueing subsystem drop counters track key functionality of this
       subsystem such as oversubscription, memory-limit, incorrect-state, and
       loopback drops.";
    uses ncs_template_pipeline-drops-common;
    leaf memory-limit {
      type oc-yang:ncs_template_counter64;
      description
        "Packets dropped due to running out of the queue memory.";
    }
    leaf incorrect-state {
      type oc-yang:ncs_template_counter64;
      description
        "Packets dropped due to hardware of software incorrect state of VOQs,
         or fabric queues, or interface queues.";
    }
    leaf lookup-queue {
      type oc-yang:ncs_template_counter64;
      description
        "Packets dropped in either the lookup or recirculation path.";
    }
  }

  grouping ncs_template_pipeline-drop-packet-fabric-block-state {
    description
      "The IC fabric subsystem drop counters track key functionality of this
       subsystem such as oversubscription, lost-packets, high and low priority
       packet drops.";
    uses ncs_template_pipeline-drops-common;
    leaf lost-packets {
      type oc-yang:ncs_template_counter64;
      description
        "Fabric drops due to re-ordering, or due to packets arriving late, or
         due to some loss in the fabric.";
    }
    uses ncs_template_pipeline-drops-common-high-low;
    leaf fabric-aggregate {
      type oc-yang:ncs_template_counter64;
      description
        "Aggregate of fabric-in and fabric-out drops.";
    }
  }

  grouping ncs_template_pipeline-drop-packet-host-interface-block-state {
    description
      "The IC host interface drop counters track key funcitonality of this
       subsystem such as oversubscription, rate-limit, fragment, and
       hi/low priority drop counts";
    uses ncs_template_pipeline-drops-common;
    leaf rate-limit {
      type oc-yang:ncs_template_counter64;
      description
        "Packet drops due to the rate limit in the integrated-circuit host
         subsystem block.";
    }
    uses ncs_template_pipeline-drops-common-high-low;
    leaf fragment-punt {
      type oc-yang:ncs_template_counter64;
      description
        "The packets that were failed to punt to CPU due to policing rate.";
    }
    leaf host-aggregate {
      type oc-yang:ncs_template_counter64;
      description
        "Aggregate of all the drops in the host path.";
    }
  }

  grouping ncs_template_pipeline-errors-common {
    description
      "A common set of error counters that apply to multiple error sections.";
    leaf name {
      type string;
      description
        "Name of the interrupt, hardware error, or software error in the NPU.";
    }
    leaf count {
      type string;
      description
        "Total count of errors of this type.";
    }
    leaf threshold {
      type string;
      description
        "Number of errors before a recovery action is automatically
         taken by the system.";
    }
    leaf-list action {
      // NCS patched for predictable order
      ordered-by user;
      type string;
      description
        "Error actions that are taken by the system - log, linecard reboot,
         linecard offline, NPU reset, NPU offline, gather diagnostic data,
         raise an alarm.";
    }
    leaf active {
      type string;
      description
        "The error is currently in an active state. When the system detects
         that the specified threshold is exceeded, this value should be set to
         true.";
      // NCS drop default statement
      oc-ext:telemetry-on-change;
    }
    leaf level {
      type string;
      description
        "The severity of the error that is being recorded by the system. This
         value can be used by a consumer to determine the action when this error
         is recorded.";
    }
  }

  grouping ncs_template_pipeline-errors-packet-interface-block-state {
    description
      "Error counter will aggregate the errors that connect the IC to the
       external MAC or PHY. Each error should contain the name, count,
       last-occurrence, threshold, action, and severity level.";
    uses ncs_template_pipeline-errors-common;
  }

  grouping ncs_template_pipeline-errors-packet-lookup-block-state {
    description
      "The IC lookup subsystem error counters include the errors encountered by
       the lookup subsystem. Each error should contain the name, count,
       last-occurrence, threshold, action, and severity level.";
    uses ncs_template_pipeline-errors-common;
  }

  grouping ncs_template_pipeline-errors-packet-queueing-block-state {
    description
      "The IC queueing subsystem error counters include the errors encountered
       by the queueing subsystem. Each error should contain the name, count,
       last-occurrence, threshold, action, and severity level.";
    uses ncs_template_pipeline-errors-common;
  }

  grouping ncs_template_pipeline-errors-packet-fabric-block-state {
    description
      "The IC fabric subsystem error counters include the errors encountered by
       the fabric subsystem. Each error should contain the name, count,
       last-occurrence, threshold, action, and severity level.";
    uses ncs_template_pipeline-errors-common;
  }

  grouping ncs_template_pipeline-errors-packet-host-interface-block-state {
    description
      "The IC host interface error counters include the errors encountered by
       the host interface subsystem. Each error should contain the name, count,
       last-occurrence, threshold, action, and severity level.";
    uses ncs_template_pipeline-errors-common;
  }

  grouping ncs_rpc_notif_platform-pipeline-top {
    description
      "Top-level structural grouping for platform pipeline
       counters.";
    container pipeline-counters {
      description
        "Top-level container for the packet, drop, and error counters for the
         five NPU sub-blocks.";
      config false;
      container packet {
        description
          "IC packet counters for all five NPU sub-blocks.";
        container interface-block {
          description
            "The IC interface subsystem connects the IC to the external PHY or
             MAC.";
          container state {
            description
              "State and counters corresponding to the interface subsystem of
               the IC.";
            uses ncs_rpc_notif_pipeline-counters-packet-interface-block-state;
          }
        }
        container lookup-block {
          description
            "The IC lookup subsystem perform the next hop lookup of the packet
             and other forwarding features such as firewall filters.";
          container state {
            description
              "State and counters corresponding to the lookup subsystem of the
               IC.";
            uses ncs_rpc_notif_pipeline-counters-packet-lookup-block-state;
          }
        }
        container queueing-block {
          description
            "The IC queueing subsystem buffers the packet while processing it
             and queues the packet for delivery to the next stage";
          container state {
            description
              "State and counters corresponding to the queueing subsystem of
               the IC.";
            uses ncs_rpc_notif_pipeline-counters-packet-queueing-block-state;
          }
        }
        container fabric-block {
          description
            "The IC fabric block subsystem connects the IC to the external
             systems fabric subsystem";
          container state {
            description
              "State and counters corresponding to the fabric subsystem of the
               IC.";
            uses ncs_rpc_notif_pipeline-counters-packet-fabric-block-state;
          }
        }
        container host-interface-block {
          description
            "The IC host interface block subsystem connects the IC to the
             external systems host or control subsystem";
          container state {
            description
              "State and counters corresponding to the host interface subsystem
               of the IC.";
            uses ncs_rpc_notif_pipeline-counters-packet-host-interface-block-state;
          }
        }
      }
      container drop {
        description
          "IC drop counters for all five NPU sub-blocks.";
        container interface-block {
          description
            "The IC interface subsystem connects the IC to the external PHY or
             MAC.";
          container state {
            description
              "Drop counters corresponding to the interface subsystem of the
               IC.";
            uses ncs_rpc_notif_pipeline-drop-packet-interface-block-state;
          }
        }
        container lookup-block {
          description
            "The IC lookup subsystem perform the next hop lookup of the packet
             and other forwarding features such as firewall filters.";
          container state {
            description
              "Drop counters corresponding to the lookup subsystem of the IC.";
            uses ncs_rpc_notif_pipeline-drop-packet-lookup-block-state;
          }
        }
        container queueing-block {
          description
            "The IC queueing subsystem buffers the packet while processing it
             and queues the packet for delivery to the next stage";
          container state {
            description
              "Drop counters corresponding to the queueing subsystem of the
               IC.";
            uses ncs_rpc_notif_pipeline-drop-packet-queueing-block-state;
          }
        }
        container fabric-block {
          description
            "The IC fabric block subsystem connects the IC to the external
             systems fabric subsystem";
          container state {
            description
              "Drop counters corresponding to the fabric subsystem of the IC.";
            uses ncs_rpc_notif_pipeline-drop-packet-fabric-block-state;
          }
        }
        container host-interface-block {
          description
            "The IC host interface block subsystem connects the IC to the
             external systems host or control subsystem";
          container state {
            description
              "Drop counters corresponding to the host interface subsystem of
               the IC.";
            uses ncs_rpc_notif_pipeline-drop-packet-host-interface-block-state;
          }
        }
      }
      container errors {
        description
          "IC errors for all five NPU sub-blocks.";
        container interface-block {
          description
            "The IC interface subsystem connects the IC to the external PHY or
             MAC.";
          list interface-block-error {
            key "name";
            description
              "An individual error within the interface block. Each error counter
               is uniquely identified by the name of the error.";
            leaf name {
              type leafref {
                path "../state/name";
              }
              description
                "Reference to the name of the error being described.";
            }
            container state {
              description
                "Errors corresponding to the interface subsystem of the IC.";
              uses ncs_rpc_notif_pipeline-errors-packet-interface-block-state;
            }
          }
        }
        container lookup-block {
          description
            "The IC lookup subsystem perform the next hop lookup of the packet
             and other forwarding features such as firewall filters.";
          list lookup-block-error {
            key "name";
            description
              "An individual error within the lookup block. Each error counter
               is uniquely identified by the name of the error.";
            leaf name {
              type leafref {
                path "../state/name";
              }
              description
                "Reference to the name of the error being described.";
            }
            container state {
              description
                "Errors corresponding to the lookup subsystem of the IC.";
              uses ncs_rpc_notif_pipeline-errors-packet-lookup-block-state;
            }
          }
        }
        container queueing-block {
          description
            "The IC queueing subsystem buffers the packet while processing it
             and queues the packet for delivery to the next stage";
          list queueing-block-error {
            key "name";
            description
              "An individual error within the queueing block. Each error counter
               is uniquely identified by the name of the error.";
            leaf name {
              type leafref {
                path "../state/name";
              }
              description
                "Reference to the name of the error being described.";
            }
            container state {
              description
                "Errors corresponding to the queueing subsystem of the IC.";
              uses ncs_rpc_notif_pipeline-errors-packet-queueing-block-state;
            }
          }
        }
        container fabric-block {
          description
            "The IC fabric block subsystem connects the IC to the external
             systems fabric subsystem";
          list fabric-block-error {
            key "name";
            description
              "An individual error within the fabric block. Each error counter
               is uniquely identified by the name of the error.";
            leaf name {
              type leafref {
                path "../state/name";
              }
              description
                "Reference to the name of the error being described.";
            }
            container state {
              description
                "Errors corresponding to the fabric subsystem of the IC.";
              uses ncs_rpc_notif_pipeline-errors-packet-fabric-block-state;
            }
          }
        }
        container host-interface-block {
          description
            "The IC host interface block subsystem connects the IC to the
             external systems host or control subsystem";
          list host-interface-error {
            key "name";
            description
              "An individual error within the host interface block. Each error
               counter is uniquely identified by the name of the error.";
            leaf name {
              type leafref {
                path "../state/name";
              }
              description
                "Reference to the name of the error being described.";
            }
            container state {
              description
                "Errors corresponding to the host interface subsystem of
                 the IC.";
              uses ncs_rpc_notif_pipeline-errors-packet-host-interface-block-state;
            }
          }
        }
      }
    }
  }

  grouping ncs_rpc_notif_pipeline-packets-common {
    description
      "A common set of packet counters that apply to multiple packet sections.";
    leaf in-packets {
      type oc-yang:ncs_rpc_notif_counter64;
      description
        "Incoming packets towards the integrated-circuit interface
         subsystem block from the line interfaces or fabric.";
    }
    leaf out-packets {
      type oc-yang:ncs_rpc_notif_counter64;
      description
        "Outgoing packets towards the line interfaces or fabric from the
         integrated-circuit interface subsystem block.";
    }
    leaf in-bytes {
      type oc-yang:ncs_rpc_notif_counter64;
      description
        "Incoming bytes towards the integrated-circuit interface
         subsystem block from the line interfaces or fabric.";
    }
    leaf out-bytes {
      type oc-yang:ncs_rpc_notif_counter64;
      description
        "Outgoing bytes towards the line interfaces or fabric from the
         integrated-circuit interface subsystem block.";
    }
  }

  grouping ncs_rpc_notif_pipeline-counters-common-high-low-packets {
    description
      "A common set of high and low priority packet counters that apply to
       multiple packet sections.";
    leaf in-high-priority-packets {
      type oc-yang:ncs_rpc_notif_counter64;
      description
        "Incoming high priority packets towards the integrated-circuit
         fabric subsystem block from the previous NPU sub block.";
    }
    leaf out-high-priority-packets {
      type oc-yang:ncs_rpc_notif_counter64;
      description
        "Outgoing high priority packets towards the fabric from the
         integrated-circuit fabric subsystem block.";
    }
    leaf in-low-priority-packets {
      type oc-yang:ncs_rpc_notif_counter64;
      description
        "Incoming low priority packets towards the integrated-circuit fabric
         subsystem block from the previous NPU sub block.";
    }
    leaf out-low-priority-packets {
      type oc-yang:ncs_rpc_notif_counter64;
      description
        "Outgoing low priority packets towards the fabric from the
         integrated-circuit fabric subsystem block.";
    }
  }

  grouping ncs_rpc_notif_pipeline-counters-packet-interface-block-state {
    description
      "Each counter will aggregate incoming and outgoing packets and bytes
       that connect the IC to the external MAC or PHY.";
    uses ncs_rpc_notif_pipeline-packets-common;
  }

  grouping ncs_rpc_notif_pipeline-counters-packet-lookup-block-state {
    description
      "The IC lookup subsystem counters include total packets/bytes in/out of
       the lookup subsystem and performance metrics for key functionality of this
       subsystem such as lookup memory usage, nexthop memory usage, ACL,
       and firewall usage";
    leaf lookup-utilization {
      type oc-types:ncs_rpc_notif_percentage;
      description
        "The integrated-circuit lookup subsystem block utilization percentage.";
    }
    uses ncs_rpc_notif_pipeline-packets-common;
    leaf lookup-memory {
      type uint64;
      units "bytes";
      description
        "The total amount of memory available in the lookup subsystem.";
    }
    leaf lookup-memory-used {
      type uint64;
      units "bytes";
      description
        "The amount of memory used in the lookup subsystem.";
    }
    leaf nexthop-memory {
      type uint64;
      units "bytes";
      description
        "The total amount of nexthop memory available in the lookup subsystem.";
    }
    leaf nexthop-memory-used {
      type uint64;
      units "bytes";
      description
        "The amount of nexthops memory used in the lookup subsystem.";
    }
    leaf acl-memory-total-entries {
      type uint64;
      description
        "Total firewall or ACL memory counter measured in entries.";
    }
    leaf acl-memory-used-entries {
      type uint64;
      description
        "Amount of used firewall or ACL memory counter measured in entries.
         The number of used entries must include the entries
         that are 'allocated but free' if the memory reaping algorithm makes
         these entries practically unusable.";
    }
    leaf acl-memory-total-bytes {
      type uint64;
      units "bytes";
      description
        "Total firewall or ACL memory counter measured in bytes.";
    }
    leaf acl-memory-used-bytes {
      type uint64;
      units "bytes";
      description
        "Amount of used firewall or ACL memory counter measured in bytes.
         The number of used bytes must include the bytes
         that are 'allocated but free' if the memory reaping algorithm makes
         these bytes practically unusable";
    }
    leaf fragment-total-pkts {
      type oc-yang:ncs_rpc_notif_counter64;
      description
        "Total number of fragments generated by the CPU.";
    }
  }

  grouping ncs_rpc_notif_pipeline-counters-packet-queueing-block-state {
    description
      "The IC queueing subsystem counters include packets/bytes in/out of the
       queueing subsystem and performance metrics for key functionality of this
       subsystem such as memory used and loopback counts.";
    uses ncs_rpc_notif_pipeline-packets-common;
    leaf queue-memory {
      type uint64;
      units "bytes";
      description
        "The total amount of memory available in the queue subsystem.";
    }
    leaf queue-memory-used {
      type uint64;
      units "bytes";
      description
        "The amount of memory used in the queue subsystem.";
    }
    leaf loopback-packets {
      type oc-yang:ncs_rpc_notif_counter64;
      description
        "The number of packets in the loopback or re-circulate subsystem.";
    }
    leaf loopback-bytes {
      type uint64;
      units "bytes";
      description
        "The number of bytes in the loopback or re-circulate subsystem.";
    }
  }

  grouping ncs_rpc_notif_pipeline-counters-packet-fabric-block-state {
    description
      "The IC fabric subsystem counters include packets/cells in/out of the
       fabric subsystem and performance metrics for key functionality of this
       subsystem such as high and low priority packet counts.";
    leaf in-cells {
      type oc-yang:ncs_rpc_notif_counter64;
      description
        "Incoming cells towards the integrated-circuit fabric
         subsystem block from the previous NPU sub block.";
    }
    leaf out-cells {
      type oc-yang:ncs_rpc_notif_counter64;
      description
        "Outgoing cells towards the fabric from the
         integrated-circuit fabric subsystem block.";
    }
    uses ncs_rpc_notif_pipeline-packets-common;
    leaf in-high-priority-cells {
      type oc-yang:ncs_rpc_notif_counter64;
      description
        "Incoming high priority cells towards the integrated-circuit fabric
         subsystem block from the previous NPU sub block.";
    }
    leaf out-high-priority-cells {
      type oc-yang:ncs_rpc_notif_counter64;
      description
        "Outgoing high priority cells towards the fabric from the
         integrated-circuit fabric subsystem block.";
    }
    leaf in-low-priority-cells {
      type oc-yang:ncs_rpc_notif_counter64;
      description
        "Incoming low priority cells towards the integrated-circuit fabric
         subsystem block from the previous NPU sub block.";
    }
    leaf out-low-priority-cells {
      type oc-yang:ncs_rpc_notif_counter64;
      description
        "Outgoing low priority cells towards the fabric from the
         integrated-circuit fabric subsystem block.";
    }
    uses ncs_rpc_notif_pipeline-counters-common-high-low-packets;
  }

  grouping ncs_rpc_notif_pipeline-counters-packet-host-interface-block-state {
    description
      "The IC host interface counters include packets/bytes in/out of the
       host interface subsystem and performance metrics for key functionality
       of this subsystem such as fragmented packet counts and hi/low priority
       packet counts";
    uses ncs_rpc_notif_pipeline-packets-common;
    leaf fragment-punt-pkts {
      type oc-yang:ncs_rpc_notif_counter64;
      description
        "The packets that were successfully punted to CPU due to egress MTU
         exceeded.";
    }
    uses ncs_rpc_notif_pipeline-counters-common-high-low-packets;
  }

  grouping ncs_rpc_notif_pipeline-drops-common {
    description
      "A common set of drop counters that apply to multiple drop sections.";
    leaf oversubscription {
      type oc-yang:ncs_rpc_notif_counter64;
      description
        "Number of packets dropped due to oversubscription of the
         integrated-circuit subsystem block.";
    }
  }

  grouping ncs_rpc_notif_pipeline-drops-common-high-low {
    description
      "A common set of drop counters for high and low priority.";
    leaf in-high-priority {
      type oc-yang:ncs_rpc_notif_counter64;
      description
        "Incoming high priority drops towards this integrated-circuit
         subsystem block from the previous NPU sub-block or interface.";
    }
    leaf out-high-priority {
      type oc-yang:ncs_rpc_notif_counter64;
      description
        "Outgoing high priority drops towards the fabric/interface from this
         integrated-circuit subsystem block.";
    }
    leaf in-low-priority {
      type oc-yang:ncs_rpc_notif_counter64;
      description
        "Incoming low priority drops towards this integrated-circuit
         subsystem block from the previous NPU sub-block or interface.";
    }
    leaf out-low-priority {
      type oc-yang:ncs_rpc_notif_counter64;
      description
        "Outgoing low priority drops towards the fabric/interface from this
         integrated-circuit subsystem block.";
    }
  }

  grouping ncs_rpc_notif_pipeline-drop-packet-interface-block-state {
    description
      "Each drop counter will aggregate incoming and outgoing packets, and
       oversubscription drops that connect the IC to the external MAC or PHY.";
    uses ncs_rpc_notif_pipeline-drops-common;
    leaf in-drops {
      type oc-yang:ncs_rpc_notif_counter64;
      description
        "Incoming drops towards the integrated-circuit interface
         subsystem block from the interfaces due to any reason.";
    }
    leaf out-drops {
      type oc-yang:ncs_rpc_notif_counter64;
      description
        "Outgoing drops towards the interfaces from the
         integrated-circuit interface subsystem block due to any reason.";
    }
  }

  grouping ncs_rpc_notif_pipeline-drop-packet-lookup-block-state {
    description
      "The IC lookup subsystem drop counters track key functionality of this
       subsystem such as Oversubscription, no-route, no-label, no-NH, invalid-
       packets, forwarding-policy, incorrect-software, rate-limit, fragments,
       and firewall drops";
    uses ncs_rpc_notif_pipeline-drops-common;
    leaf no-route {
      type oc-yang:ncs_rpc_notif_counter64;
      description
        "Packets dropped due to no FIB entry for this ipv4 or ipv6 lookup.";
    }
    leaf no-label {
      type oc-yang:ncs_rpc_notif_counter64;
      description
        "Packets dropped due to no FIB entry for this MPLS label.";
    }
    leaf no-nexthop {
      type oc-yang:ncs_rpc_notif_counter64;
      description
        "Packets dropped due to no nexthop information - either the nexthop is
         not programmed, or there is an invalid nexthop, or there is no ARP
         information so the nexthop is in invalid state.";
    }
    leaf invalid-packet {
      type oc-yang:ncs_rpc_notif_counter64;
      description
        "Packets dropped due to invalid packet format for ipv4, ipv6, or MPLS.";
    }
    leaf forwarding-policy {
      type oc-yang:ncs_rpc_notif_counter64;
      description
        "Packets dropped due to either a filter applied as part of a forwarding
         policy or dropped due to a policy-based-routing policy lookup.";
    }
    leaf incorrect-software-state {
      type oc-yang:ncs_rpc_notif_counter64;
      description
        "Packets dropped due to any incorrect or invalid software state of the
         forwarding structures during lookup.";
    }
    leaf rate-limit {
      type oc-yang:ncs_rpc_notif_counter64;
      description
        "Packets dropped due to rate limiters - either user configured rate
         limiters or system rate limiters in the forwarding path.";
    }
    leaf fragment-total-drops {
      type oc-yang:ncs_rpc_notif_counter64;
      description
        "Total number of packets dropped that could not be fragmented by NPU
         due to DF bit.";
    }
    leaf lookup-aggregate {
      type oc-yang:ncs_rpc_notif_counter64;
      description
        "Packets dropped due to aggregate lookup drop counters - this counter
         is sometimes referred to as Normal Discards or
         ENQ_DISCARDED_PACKET_COUNTER.";
    }
    leaf acl-drops {
      type oc-yang:ncs_rpc_notif_counter64;
      description
        "Packets dropped due to firewall or acl terms.";
    }
  }

  grouping ncs_rpc_notif_pipeline-drop-packet-queueing-block-state {
    description
      "The IC queueing subsystem drop counters track key functionality of this
       subsystem such as oversubscription, memory-limit, incorrect-state, and
       loopback drops.";
    uses ncs_rpc_notif_pipeline-drops-common;
    leaf memory-limit {
      type oc-yang:ncs_rpc_notif_counter64;
      description
        "Packets dropped due to running out of the queue memory.";
    }
    leaf incorrect-state {
      type oc-yang:ncs_rpc_notif_counter64;
      description
        "Packets dropped due to hardware of software incorrect state of VOQs,
         or fabric queues, or interface queues.";
    }
    leaf lookup-queue {
      type oc-yang:ncs_rpc_notif_counter64;
      description
        "Packets dropped in either the lookup or recirculation path.";
    }
  }

  grouping ncs_rpc_notif_pipeline-drop-packet-fabric-block-state {
    description
      "The IC fabric subsystem drop counters track key functionality of this
       subsystem such as oversubscription, lost-packets, high and low priority
       packet drops.";
    uses ncs_rpc_notif_pipeline-drops-common;
    leaf lost-packets {
      type oc-yang:ncs_rpc_notif_counter64;
      description
        "Fabric drops due to re-ordering, or due to packets arriving late, or
         due to some loss in the fabric.";
    }
    uses ncs_rpc_notif_pipeline-drops-common-high-low;
    leaf fabric-aggregate {
      type oc-yang:ncs_rpc_notif_counter64;
      description
        "Aggregate of fabric-in and fabric-out drops.";
    }
  }

  grouping ncs_rpc_notif_pipeline-drop-packet-host-interface-block-state {
    description
      "The IC host interface drop counters track key funcitonality of this
       subsystem such as oversubscription, rate-limit, fragment, and
       hi/low priority drop counts";
    uses ncs_rpc_notif_pipeline-drops-common;
    leaf rate-limit {
      type oc-yang:ncs_rpc_notif_counter64;
      description
        "Packet drops due to the rate limit in the integrated-circuit host
         subsystem block.";
    }
    uses ncs_rpc_notif_pipeline-drops-common-high-low;
    leaf fragment-punt {
      type oc-yang:ncs_rpc_notif_counter64;
      description
        "The packets that were failed to punt to CPU due to policing rate.";
    }
    leaf host-aggregate {
      type oc-yang:ncs_rpc_notif_counter64;
      description
        "Aggregate of all the drops in the host path.";
    }
  }

  grouping ncs_rpc_notif_pipeline-errors-common {
    description
      "A common set of error counters that apply to multiple error sections.";
    leaf name {
      type string;
      description
        "Name of the interrupt, hardware error, or software error in the NPU.";
    }
    leaf count {
      type uint64;
      description
        "Total count of errors of this type.";
    }
    leaf threshold {
      type uint64;
      description
        "Number of errors before a recovery action is automatically
         taken by the system.";
    }
    leaf-list action {
      type enumeration {
        enum "LOG" {
          description
            "Log a descriptive message.";
        }
        enum "LINECARD_REBOOT" {
          description
            "The line card is brought offline and then back online.";
        }
        enum "LINECARD_OFFLINE" {
          description
            "The line card is brought offline.";
        }
        enum "NPU_RESET" {
          description
            "The NPU is brought offline and then back online.";
        }
        enum "NPU_OFFLINE" {
          description
            "The NPU is brought offline.";
        }
        enum "GET_DIAGNOSTIC_INFO" {
          description
            "Diagnostic data is gathered at the time of the problem.";
        }
        enum "ALARM" {
          description
            "An Alarm is raised";
        }
      }
      description
        "Error actions that are taken by the system - log, linecard reboot,
         linecard offline, NPU reset, NPU offline, gather diagnostic data,
         raise an alarm.";
    }
    leaf active {
      type boolean;
      description
        "The error is currently in an active state. When the system detects
         that the specified threshold is exceeded, this value should be set to
         true.";
      default "false";
      oc-ext:telemetry-on-change;
    }
    leaf level {
      type enumeration {
        enum "FATAL" {
          description
            "The Fatal error causes total packet loss";
        }
        enum "MAJOR" {
          description
            "The Major error causes persistent packet loss";
        }
        enum "MINOR" {
          description
            "The Minor error is an indication of some past problem, but now is
             corrected";
        }
        enum "INFORMATIONAL" {
          description
            "Some problem happened that is not packet loss affecting.";
        }
      }
      description
        "The severity of the error that is being recorded by the system. This
         value can be used by a consumer to determine the action when this error
         is recorded.";
    }
  }

  grouping ncs_rpc_notif_pipeline-errors-packet-interface-block-state {
    description
      "Error counter will aggregate the errors that connect the IC to the
       external MAC or PHY. Each error should contain the name, count,
       last-occurrence, threshold, action, and severity level.";
    uses ncs_rpc_notif_pipeline-errors-common;
  }

  grouping ncs_rpc_notif_pipeline-errors-packet-lookup-block-state {
    description
      "The IC lookup subsystem error counters include the errors encountered by
       the lookup subsystem. Each error should contain the name, count,
       last-occurrence, threshold, action, and severity level.";
    uses ncs_rpc_notif_pipeline-errors-common;
  }

  grouping ncs_rpc_notif_pipeline-errors-packet-queueing-block-state {
    description
      "The IC queueing subsystem error counters include the errors encountered
       by the queueing subsystem. Each error should contain the name, count,
       last-occurrence, threshold, action, and severity level.";
    uses ncs_rpc_notif_pipeline-errors-common;
  }

  grouping ncs_rpc_notif_pipeline-errors-packet-fabric-block-state {
    description
      "The IC fabric subsystem error counters include the errors encountered by
       the fabric subsystem. Each error should contain the name, count,
       last-occurrence, threshold, action, and severity level.";
    uses ncs_rpc_notif_pipeline-errors-common;
  }

  grouping ncs_rpc_notif_pipeline-errors-packet-host-interface-block-state {
    description
      "The IC host interface error counters include the errors encountered by
       the host interface subsystem. Each error should contain the name, count,
       last-occurrence, threshold, action, and severity level.";
    uses ncs_rpc_notif_pipeline-errors-common;
  }

  grouping live_ncs_platform-pipeline-top {
    description
      "Top-level structural grouping for platform pipeline
       counters.";
    container pipeline-counters {
      description
        "Top-level container for the packet, drop, and error counters for the
         five NPU sub-blocks.";
      container packet {
        description
          "IC packet counters for all five NPU sub-blocks.";
        container interface-block {
          description
            "The IC interface subsystem connects the IC to the external PHY or
             MAC.";
          container state {
            description
              "State and counters corresponding to the interface subsystem of
               the IC.";
            uses live_ncs_pipeline-counters-packet-interface-block-state;
          }
        }
        container lookup-block {
          description
            "The IC lookup subsystem perform the next hop lookup of the packet
             and other forwarding features such as firewall filters.";
          container state {
            description
              "State and counters corresponding to the lookup subsystem of the
               IC.";
            uses live_ncs_pipeline-counters-packet-lookup-block-state;
          }
        }
        container queueing-block {
          description
            "The IC queueing subsystem buffers the packet while processing it
             and queues the packet for delivery to the next stage";
          container state {
            description
              "State and counters corresponding to the queueing subsystem of
               the IC.";
            uses live_ncs_pipeline-counters-packet-queueing-block-state;
          }
        }
        container fabric-block {
          description
            "The IC fabric block subsystem connects the IC to the external
             systems fabric subsystem";
          container state {
            description
              "State and counters corresponding to the fabric subsystem of the
               IC.";
            uses live_ncs_pipeline-counters-packet-fabric-block-state;
          }
        }
        container host-interface-block {
          description
            "The IC host interface block subsystem connects the IC to the
             external systems host or control subsystem";
          container state {
            description
              "State and counters corresponding to the host interface subsystem
               of the IC.";
            uses live_ncs_pipeline-counters-packet-host-interface-block-state;
          }
        }
      }
      container drop {
        description
          "IC drop counters for all five NPU sub-blocks.";
        container interface-block {
          description
            "The IC interface subsystem connects the IC to the external PHY or
             MAC.";
          container state {
            description
              "Drop counters corresponding to the interface subsystem of the
               IC.";
            uses live_ncs_pipeline-drop-packet-interface-block-state;
          }
        }
        container lookup-block {
          description
            "The IC lookup subsystem perform the next hop lookup of the packet
             and other forwarding features such as firewall filters.";
          container state {
            description
              "Drop counters corresponding to the lookup subsystem of the IC.";
            uses live_ncs_pipeline-drop-packet-lookup-block-state;
          }
        }
        container queueing-block {
          description
            "The IC queueing subsystem buffers the packet while processing it
             and queues the packet for delivery to the next stage";
          container state {
            description
              "Drop counters corresponding to the queueing subsystem of the
               IC.";
            uses live_ncs_pipeline-drop-packet-queueing-block-state;
          }
        }
        container fabric-block {
          description
            "The IC fabric block subsystem connects the IC to the external
             systems fabric subsystem";
          container state {
            description
              "Drop counters corresponding to the fabric subsystem of the IC.";
            uses live_ncs_pipeline-drop-packet-fabric-block-state;
          }
        }
        container host-interface-block {
          description
            "The IC host interface block subsystem connects the IC to the
             external systems host or control subsystem";
          container state {
            description
              "Drop counters corresponding to the host interface subsystem of
               the IC.";
            uses live_ncs_pipeline-drop-packet-host-interface-block-state;
          }
        }
      }
      container errors {
        description
          "IC errors for all five NPU sub-blocks.";
        container interface-block {
          description
            "The IC interface subsystem connects the IC to the external PHY or
             MAC.";
          list interface-block-error {
            key "name";
            description
              "An individual error within the interface block. Each error counter
               is uniquely identified by the name of the error.";
            leaf name {
              type leafref {
                path "../state/name";
              }
              description
                "Reference to the name of the error being described.";
            }
            container state {
              description
                "Errors corresponding to the interface subsystem of the IC.";
              uses live_ncs_pipeline-errors-packet-interface-block-state;
            }
          }
        }
        container lookup-block {
          description
            "The IC lookup subsystem perform the next hop lookup of the packet
             and other forwarding features such as firewall filters.";
          list lookup-block-error {
            key "name";
            description
              "An individual error within the lookup block. Each error counter
               is uniquely identified by the name of the error.";
            leaf name {
              type leafref {
                path "../state/name";
              }
              description
                "Reference to the name of the error being described.";
            }
            container state {
              description
                "Errors corresponding to the lookup subsystem of the IC.";
              uses live_ncs_pipeline-errors-packet-lookup-block-state;
            }
          }
        }
        container queueing-block {
          description
            "The IC queueing subsystem buffers the packet while processing it
             and queues the packet for delivery to the next stage";
          list queueing-block-error {
            key "name";
            description
              "An individual error within the queueing block. Each error counter
               is uniquely identified by the name of the error.";
            leaf name {
              type leafref {
                path "../state/name";
              }
              description
                "Reference to the name of the error being described.";
            }
            container state {
              description
                "Errors corresponding to the queueing subsystem of the IC.";
              uses live_ncs_pipeline-errors-packet-queueing-block-state;
            }
          }
        }
        container fabric-block {
          description
            "The IC fabric block subsystem connects the IC to the external
             systems fabric subsystem";
          list fabric-block-error {
            key "name";
            description
              "An individual error within the fabric block. Each error counter
               is uniquely identified by the name of the error.";
            leaf name {
              type leafref {
                path "../state/name";
              }
              description
                "Reference to the name of the error being described.";
            }
            container state {
              description
                "Errors corresponding to the fabric subsystem of the IC.";
              uses live_ncs_pipeline-errors-packet-fabric-block-state;
            }
          }
        }
        container host-interface-block {
          description
            "The IC host interface block subsystem connects the IC to the
             external systems host or control subsystem";
          list host-interface-error {
            key "name";
            description
              "An individual error within the host interface block. Each error
               counter is uniquely identified by the name of the error.";
            leaf name {
              type leafref {
                path "../state/name";
              }
              description
                "Reference to the name of the error being described.";
            }
            container state {
              description
                "Errors corresponding to the host interface subsystem of
                 the IC.";
              uses live_ncs_pipeline-errors-packet-host-interface-block-state;
            }
          }
        }
      }
    }
  }

  grouping live_ncs_pipeline-packets-common {
    description
      "A common set of packet counters that apply to multiple packet sections.";
    leaf in-packets {
      type oc-yang:live_ncs_counter64;
      description
        "Incoming packets towards the integrated-circuit interface
         subsystem block from the line interfaces or fabric.";
    }
    leaf out-packets {
      type oc-yang:live_ncs_counter64;
      description
        "Outgoing packets towards the line interfaces or fabric from the
         integrated-circuit interface subsystem block.";
    }
    leaf in-bytes {
      type oc-yang:live_ncs_counter64;
      description
        "Incoming bytes towards the integrated-circuit interface
         subsystem block from the line interfaces or fabric.";
    }
    leaf out-bytes {
      type oc-yang:live_ncs_counter64;
      description
        "Outgoing bytes towards the line interfaces or fabric from the
         integrated-circuit interface subsystem block.";
    }
  }

  grouping live_ncs_pipeline-counters-common-high-low-packets {
    description
      "A common set of high and low priority packet counters that apply to
       multiple packet sections.";
    leaf in-high-priority-packets {
      type oc-yang:live_ncs_counter64;
      description
        "Incoming high priority packets towards the integrated-circuit
         fabric subsystem block from the previous NPU sub block.";
    }
    leaf out-high-priority-packets {
      type oc-yang:live_ncs_counter64;
      description
        "Outgoing high priority packets towards the fabric from the
         integrated-circuit fabric subsystem block.";
    }
    leaf in-low-priority-packets {
      type oc-yang:live_ncs_counter64;
      description
        "Incoming low priority packets towards the integrated-circuit fabric
         subsystem block from the previous NPU sub block.";
    }
    leaf out-low-priority-packets {
      type oc-yang:live_ncs_counter64;
      description
        "Outgoing low priority packets towards the fabric from the
         integrated-circuit fabric subsystem block.";
    }
  }

  grouping live_ncs_pipeline-counters-packet-interface-block-state {
    description
      "Each counter will aggregate incoming and outgoing packets and bytes
       that connect the IC to the external MAC or PHY.";
    uses live_ncs_pipeline-packets-common;
  }

  grouping live_ncs_pipeline-counters-packet-lookup-block-state {
    description
      "The IC lookup subsystem counters include total packets/bytes in/out of
       the lookup subsystem and performance metrics for key functionality of this
       subsystem such as lookup memory usage, nexthop memory usage, ACL,
       and firewall usage";
    leaf lookup-utilization {
      type oc-types:live_ncs_percentage;
      description
        "The integrated-circuit lookup subsystem block utilization percentage.";
    }
    uses live_ncs_pipeline-packets-common;
    leaf lookup-memory {
      type uint64;
      units "bytes";
      description
        "The total amount of memory available in the lookup subsystem.";
    }
    leaf lookup-memory-used {
      type uint64;
      units "bytes";
      description
        "The amount of memory used in the lookup subsystem.";
    }
    leaf nexthop-memory {
      type uint64;
      units "bytes";
      description
        "The total amount of nexthop memory available in the lookup subsystem.";
    }
    leaf nexthop-memory-used {
      type uint64;
      units "bytes";
      description
        "The amount of nexthops memory used in the lookup subsystem.";
    }
    leaf acl-memory-total-entries {
      type uint64;
      description
        "Total firewall or ACL memory counter measured in entries.";
    }
    leaf acl-memory-used-entries {
      type uint64;
      description
        "Amount of used firewall or ACL memory counter measured in entries.
         The number of used entries must include the entries
         that are 'allocated but free' if the memory reaping algorithm makes
         these entries practically unusable.";
    }
    leaf acl-memory-total-bytes {
      type uint64;
      units "bytes";
      description
        "Total firewall or ACL memory counter measured in bytes.";
    }
    leaf acl-memory-used-bytes {
      type uint64;
      units "bytes";
      description
        "Amount of used firewall or ACL memory counter measured in bytes.
         The number of used bytes must include the bytes
         that are 'allocated but free' if the memory reaping algorithm makes
         these bytes practically unusable";
    }
    leaf fragment-total-pkts {
      type oc-yang:live_ncs_counter64;
      description
        "Total number of fragments generated by the CPU.";
    }
  }

  grouping live_ncs_pipeline-counters-packet-queueing-block-state {
    description
      "The IC queueing subsystem counters include packets/bytes in/out of the
       queueing subsystem and performance metrics for key functionality of this
       subsystem such as memory used and loopback counts.";
    uses live_ncs_pipeline-packets-common;
    leaf queue-memory {
      type uint64;
      units "bytes";
      description
        "The total amount of memory available in the queue subsystem.";
    }
    leaf queue-memory-used {
      type uint64;
      units "bytes";
      description
        "The amount of memory used in the queue subsystem.";
    }
    leaf loopback-packets {
      type oc-yang:live_ncs_counter64;
      description
        "The number of packets in the loopback or re-circulate subsystem.";
    }
    leaf loopback-bytes {
      type uint64;
      units "bytes";
      description
        "The number of bytes in the loopback or re-circulate subsystem.";
    }
  }

  grouping live_ncs_pipeline-counters-packet-fabric-block-state {
    description
      "The IC fabric subsystem counters include packets/cells in/out of the
       fabric subsystem and performance metrics for key functionality of this
       subsystem such as high and low priority packet counts.";
    leaf in-cells {
      type oc-yang:live_ncs_counter64;
      description
        "Incoming cells towards the integrated-circuit fabric
         subsystem block from the previous NPU sub block.";
    }
    leaf out-cells {
      type oc-yang:live_ncs_counter64;
      description
        "Outgoing cells towards the fabric from the
         integrated-circuit fabric subsystem block.";
    }
    uses live_ncs_pipeline-packets-common;
    leaf in-high-priority-cells {
      type oc-yang:live_ncs_counter64;
      description
        "Incoming high priority cells towards the integrated-circuit fabric
         subsystem block from the previous NPU sub block.";
    }
    leaf out-high-priority-cells {
      type oc-yang:live_ncs_counter64;
      description
        "Outgoing high priority cells towards the fabric from the
         integrated-circuit fabric subsystem block.";
    }
    leaf in-low-priority-cells {
      type oc-yang:live_ncs_counter64;
      description
        "Incoming low priority cells towards the integrated-circuit fabric
         subsystem block from the previous NPU sub block.";
    }
    leaf out-low-priority-cells {
      type oc-yang:live_ncs_counter64;
      description
        "Outgoing low priority cells towards the fabric from the
         integrated-circuit fabric subsystem block.";
    }
    uses live_ncs_pipeline-counters-common-high-low-packets;
  }

  grouping live_ncs_pipeline-counters-packet-host-interface-block-state {
    description
      "The IC host interface counters include packets/bytes in/out of the
       host interface subsystem and performance metrics for key functionality
       of this subsystem such as fragmented packet counts and hi/low priority
       packet counts";
    uses live_ncs_pipeline-packets-common;
    leaf fragment-punt-pkts {
      type oc-yang:live_ncs_counter64;
      description
        "The packets that were successfully punted to CPU due to egress MTU
         exceeded.";
    }
    uses live_ncs_pipeline-counters-common-high-low-packets;
  }

  grouping live_ncs_pipeline-drops-common {
    description
      "A common set of drop counters that apply to multiple drop sections.";
    leaf oversubscription {
      type oc-yang:live_ncs_counter64;
      description
        "Number of packets dropped due to oversubscription of the
         integrated-circuit subsystem block.";
    }
  }

  grouping live_ncs_pipeline-drops-common-high-low {
    description
      "A common set of drop counters for high and low priority.";
    leaf in-high-priority {
      type oc-yang:live_ncs_counter64;
      description
        "Incoming high priority drops towards this integrated-circuit
         subsystem block from the previous NPU sub-block or interface.";
    }
    leaf out-high-priority {
      type oc-yang:live_ncs_counter64;
      description
        "Outgoing high priority drops towards the fabric/interface from this
         integrated-circuit subsystem block.";
    }
    leaf in-low-priority {
      type oc-yang:live_ncs_counter64;
      description
        "Incoming low priority drops towards this integrated-circuit
         subsystem block from the previous NPU sub-block or interface.";
    }
    leaf out-low-priority {
      type oc-yang:live_ncs_counter64;
      description
        "Outgoing low priority drops towards the fabric/interface from this
         integrated-circuit subsystem block.";
    }
  }

  grouping live_ncs_pipeline-drop-packet-interface-block-state {
    description
      "Each drop counter will aggregate incoming and outgoing packets, and
       oversubscription drops that connect the IC to the external MAC or PHY.";
    uses live_ncs_pipeline-drops-common;
    leaf in-drops {
      type oc-yang:live_ncs_counter64;
      description
        "Incoming drops towards the integrated-circuit interface
         subsystem block from the interfaces due to any reason.";
    }
    leaf out-drops {
      type oc-yang:live_ncs_counter64;
      description
        "Outgoing drops towards the interfaces from the
         integrated-circuit interface subsystem block due to any reason.";
    }
  }

  grouping live_ncs_pipeline-drop-packet-lookup-block-state {
    description
      "The IC lookup subsystem drop counters track key functionality of this
       subsystem such as Oversubscription, no-route, no-label, no-NH, invalid-
       packets, forwarding-policy, incorrect-software, rate-limit, fragments,
       and firewall drops";
    uses live_ncs_pipeline-drops-common;
    leaf no-route {
      type oc-yang:live_ncs_counter64;
      description
        "Packets dropped due to no FIB entry for this ipv4 or ipv6 lookup.";
    }
    leaf no-label {
      type oc-yang:live_ncs_counter64;
      description
        "Packets dropped due to no FIB entry for this MPLS label.";
    }
    leaf no-nexthop {
      type oc-yang:live_ncs_counter64;
      description
        "Packets dropped due to no nexthop information - either the nexthop is
         not programmed, or there is an invalid nexthop, or there is no ARP
         information so the nexthop is in invalid state.";
    }
    leaf invalid-packet {
      type oc-yang:live_ncs_counter64;
      description
        "Packets dropped due to invalid packet format for ipv4, ipv6, or MPLS.";
    }
    leaf forwarding-policy {
      type oc-yang:live_ncs_counter64;
      description
        "Packets dropped due to either a filter applied as part of a forwarding
         policy or dropped due to a policy-based-routing policy lookup.";
    }
    leaf incorrect-software-state {
      type oc-yang:live_ncs_counter64;
      description
        "Packets dropped due to any incorrect or invalid software state of the
         forwarding structures during lookup.";
    }
    leaf rate-limit {
      type oc-yang:live_ncs_counter64;
      description
        "Packets dropped due to rate limiters - either user configured rate
         limiters or system rate limiters in the forwarding path.";
    }
    leaf fragment-total-drops {
      type oc-yang:live_ncs_counter64;
      description
        "Total number of packets dropped that could not be fragmented by NPU
         due to DF bit.";
    }
    leaf lookup-aggregate {
      type oc-yang:live_ncs_counter64;
      description
        "Packets dropped due to aggregate lookup drop counters - this counter
         is sometimes referred to as Normal Discards or
         ENQ_DISCARDED_PACKET_COUNTER.";
    }
    leaf acl-drops {
      type oc-yang:live_ncs_counter64;
      description
        "Packets dropped due to firewall or acl terms.";
    }
  }

  grouping live_ncs_pipeline-drop-packet-queueing-block-state {
    description
      "The IC queueing subsystem drop counters track key functionality of this
       subsystem such as oversubscription, memory-limit, incorrect-state, and
       loopback drops.";
    uses live_ncs_pipeline-drops-common;
    leaf memory-limit {
      type oc-yang:live_ncs_counter64;
      description
        "Packets dropped due to running out of the queue memory.";
    }
    leaf incorrect-state {
      type oc-yang:live_ncs_counter64;
      description
        "Packets dropped due to hardware of software incorrect state of VOQs,
         or fabric queues, or interface queues.";
    }
    leaf lookup-queue {
      type oc-yang:live_ncs_counter64;
      description
        "Packets dropped in either the lookup or recirculation path.";
    }
  }

  grouping live_ncs_pipeline-drop-packet-fabric-block-state {
    description
      "The IC fabric subsystem drop counters track key functionality of this
       subsystem such as oversubscription, lost-packets, high and low priority
       packet drops.";
    uses live_ncs_pipeline-drops-common;
    leaf lost-packets {
      type oc-yang:live_ncs_counter64;
      description
        "Fabric drops due to re-ordering, or due to packets arriving late, or
         due to some loss in the fabric.";
    }
    uses live_ncs_pipeline-drops-common-high-low;
    leaf fabric-aggregate {
      type oc-yang:live_ncs_counter64;
      description
        "Aggregate of fabric-in and fabric-out drops.";
    }
  }

  grouping live_ncs_pipeline-drop-packet-host-interface-block-state {
    description
      "The IC host interface drop counters track key funcitonality of this
       subsystem such as oversubscription, rate-limit, fragment, and
       hi/low priority drop counts";
    uses live_ncs_pipeline-drops-common;
    leaf rate-limit {
      type oc-yang:live_ncs_counter64;
      description
        "Packet drops due to the rate limit in the integrated-circuit host
         subsystem block.";
    }
    uses live_ncs_pipeline-drops-common-high-low;
    leaf fragment-punt {
      type oc-yang:live_ncs_counter64;
      description
        "The packets that were failed to punt to CPU due to policing rate.";
    }
    leaf host-aggregate {
      type oc-yang:live_ncs_counter64;
      description
        "Aggregate of all the drops in the host path.";
    }
  }

  grouping live_ncs_pipeline-errors-common {
    description
      "A common set of error counters that apply to multiple error sections.";
    leaf name {
      type string;
      description
        "Name of the interrupt, hardware error, or software error in the NPU.";
    }
    leaf count {
      type uint64;
      description
        "Total count of errors of this type.";
    }
    leaf threshold {
      type uint64;
      description
        "Number of errors before a recovery action is automatically
         taken by the system.";
    }
    leaf-list action {
      type enumeration {
        enum "LOG" {
          description
            "Log a descriptive message.";
        }
        enum "LINECARD_REBOOT" {
          description
            "The line card is brought offline and then back online.";
        }
        enum "LINECARD_OFFLINE" {
          description
            "The line card is brought offline.";
        }
        enum "NPU_RESET" {
          description
            "The NPU is brought offline and then back online.";
        }
        enum "NPU_OFFLINE" {
          description
            "The NPU is brought offline.";
        }
        enum "GET_DIAGNOSTIC_INFO" {
          description
            "Diagnostic data is gathered at the time of the problem.";
        }
        enum "ALARM" {
          description
            "An Alarm is raised";
        }
      }
      description
        "Error actions that are taken by the system - log, linecard reboot,
         linecard offline, NPU reset, NPU offline, gather diagnostic data,
         raise an alarm.";
    }
    leaf active {
      type boolean;
      description
        "The error is currently in an active state. When the system detects
         that the specified threshold is exceeded, this value should be set to
         true.";
      // NCS drop default statement
      oc-ext:telemetry-on-change;
    }
    leaf level {
      type enumeration {
        enum "FATAL" {
          description
            "The Fatal error causes total packet loss";
        }
        enum "MAJOR" {
          description
            "The Major error causes persistent packet loss";
        }
        enum "MINOR" {
          description
            "The Minor error is an indication of some past problem, but now is
             corrected";
        }
        enum "INFORMATIONAL" {
          description
            "Some problem happened that is not packet loss affecting.";
        }
      }
      description
        "The severity of the error that is being recorded by the system. This
         value can be used by a consumer to determine the action when this error
         is recorded.";
    }
  }

  grouping live_ncs_pipeline-errors-packet-interface-block-state {
    description
      "Error counter will aggregate the errors that connect the IC to the
       external MAC or PHY. Each error should contain the name, count,
       last-occurrence, threshold, action, and severity level.";
    uses live_ncs_pipeline-errors-common;
  }

  grouping live_ncs_pipeline-errors-packet-lookup-block-state {
    description
      "The IC lookup subsystem error counters include the errors encountered by
       the lookup subsystem. Each error should contain the name, count,
       last-occurrence, threshold, action, and severity level.";
    uses live_ncs_pipeline-errors-common;
  }

  grouping live_ncs_pipeline-errors-packet-queueing-block-state {
    description
      "The IC queueing subsystem error counters include the errors encountered
       by the queueing subsystem. Each error should contain the name, count,
       last-occurrence, threshold, action, and severity level.";
    uses live_ncs_pipeline-errors-common;
  }

  grouping live_ncs_pipeline-errors-packet-fabric-block-state {
    description
      "The IC fabric subsystem error counters include the errors encountered by
       the fabric subsystem. Each error should contain the name, count,
       last-occurrence, threshold, action, and severity level.";
    uses live_ncs_pipeline-errors-common;
  }

  grouping live_ncs_pipeline-errors-packet-host-interface-block-state {
    description
      "The IC host interface error counters include the errors encountered by
       the host interface subsystem. Each error should contain the name, count,
       last-occurrence, threshold, action, and severity level.";
    uses live_ncs_pipeline-errors-common;
  }

  grouping platform-pipeline-top {
    description
      "Top-level structural grouping for platform pipeline
       counters.";
    // NCS drop config false container 'pipeline-counters'
  }

  grouping pipeline-packets-common {
    description
      "A common set of packet counters that apply to multiple packet sections.";
    leaf in-packets {
      type oc-yang:counter64;
      description
        "Incoming packets towards the integrated-circuit interface
         subsystem block from the line interfaces or fabric.";
    }
    leaf out-packets {
      type oc-yang:counter64;
      description
        "Outgoing packets towards the line interfaces or fabric from the
         integrated-circuit interface subsystem block.";
    }
    leaf in-bytes {
      type oc-yang:counter64;
      description
        "Incoming bytes towards the integrated-circuit interface
         subsystem block from the line interfaces or fabric.";
    }
    leaf out-bytes {
      type oc-yang:counter64;
      description
        "Outgoing bytes towards the line interfaces or fabric from the
         integrated-circuit interface subsystem block.";
    }
  }

  grouping pipeline-counters-common-high-low-packets {
    description
      "A common set of high and low priority packet counters that apply to
       multiple packet sections.";
    leaf in-high-priority-packets {
      type oc-yang:counter64;
      description
        "Incoming high priority packets towards the integrated-circuit
         fabric subsystem block from the previous NPU sub block.";
    }
    leaf out-high-priority-packets {
      type oc-yang:counter64;
      description
        "Outgoing high priority packets towards the fabric from the
         integrated-circuit fabric subsystem block.";
    }
    leaf in-low-priority-packets {
      type oc-yang:counter64;
      description
        "Incoming low priority packets towards the integrated-circuit fabric
         subsystem block from the previous NPU sub block.";
    }
    leaf out-low-priority-packets {
      type oc-yang:counter64;
      description
        "Outgoing low priority packets towards the fabric from the
         integrated-circuit fabric subsystem block.";
    }
  }

  grouping pipeline-counters-packet-interface-block-state {
    description
      "Each counter will aggregate incoming and outgoing packets and bytes
       that connect the IC to the external MAC or PHY.";
    uses pipeline-packets-common;
  }

  grouping pipeline-counters-packet-lookup-block-state {
    description
      "The IC lookup subsystem counters include total packets/bytes in/out of
       the lookup subsystem and performance metrics for key functionality of this
       subsystem such as lookup memory usage, nexthop memory usage, ACL,
       and firewall usage";
    leaf lookup-utilization {
      type oc-types:percentage;
      description
        "The integrated-circuit lookup subsystem block utilization percentage.";
    }
    uses pipeline-packets-common;
    leaf lookup-memory {
      type uint64;
      units "bytes";
      description
        "The total amount of memory available in the lookup subsystem.";
    }
    leaf lookup-memory-used {
      type uint64;
      units "bytes";
      description
        "The amount of memory used in the lookup subsystem.";
    }
    leaf nexthop-memory {
      type uint64;
      units "bytes";
      description
        "The total amount of nexthop memory available in the lookup subsystem.";
    }
    leaf nexthop-memory-used {
      type uint64;
      units "bytes";
      description
        "The amount of nexthops memory used in the lookup subsystem.";
    }
    leaf acl-memory-total-entries {
      type uint64;
      description
        "Total firewall or ACL memory counter measured in entries.";
    }
    leaf acl-memory-used-entries {
      type uint64;
      description
        "Amount of used firewall or ACL memory counter measured in entries.
         The number of used entries must include the entries
         that are 'allocated but free' if the memory reaping algorithm makes
         these entries practically unusable.";
    }
    leaf acl-memory-total-bytes {
      type uint64;
      units "bytes";
      description
        "Total firewall or ACL memory counter measured in bytes.";
    }
    leaf acl-memory-used-bytes {
      type uint64;
      units "bytes";
      description
        "Amount of used firewall or ACL memory counter measured in bytes.
         The number of used bytes must include the bytes
         that are 'allocated but free' if the memory reaping algorithm makes
         these bytes practically unusable";
    }
    leaf fragment-total-pkts {
      type oc-yang:counter64;
      description
        "Total number of fragments generated by the CPU.";
    }
  }

  grouping pipeline-counters-packet-queueing-block-state {
    description
      "The IC queueing subsystem counters include packets/bytes in/out of the
       queueing subsystem and performance metrics for key functionality of this
       subsystem such as memory used and loopback counts.";
    uses pipeline-packets-common;
    leaf queue-memory {
      type uint64;
      units "bytes";
      description
        "The total amount of memory available in the queue subsystem.";
    }
    leaf queue-memory-used {
      type uint64;
      units "bytes";
      description
        "The amount of memory used in the queue subsystem.";
    }
    leaf loopback-packets {
      type oc-yang:counter64;
      description
        "The number of packets in the loopback or re-circulate subsystem.";
    }
    leaf loopback-bytes {
      type uint64;
      units "bytes";
      description
        "The number of bytes in the loopback or re-circulate subsystem.";
    }
  }

  grouping pipeline-counters-packet-fabric-block-state {
    description
      "The IC fabric subsystem counters include packets/cells in/out of the
       fabric subsystem and performance metrics for key functionality of this
       subsystem such as high and low priority packet counts.";
    leaf in-cells {
      type oc-yang:counter64;
      description
        "Incoming cells towards the integrated-circuit fabric
         subsystem block from the previous NPU sub block.";
    }
    leaf out-cells {
      type oc-yang:counter64;
      description
        "Outgoing cells towards the fabric from the
         integrated-circuit fabric subsystem block.";
    }
    uses pipeline-packets-common;
    leaf in-high-priority-cells {
      type oc-yang:counter64;
      description
        "Incoming high priority cells towards the integrated-circuit fabric
         subsystem block from the previous NPU sub block.";
    }
    leaf out-high-priority-cells {
      type oc-yang:counter64;
      description
        "Outgoing high priority cells towards the fabric from the
         integrated-circuit fabric subsystem block.";
    }
    leaf in-low-priority-cells {
      type oc-yang:counter64;
      description
        "Incoming low priority cells towards the integrated-circuit fabric
         subsystem block from the previous NPU sub block.";
    }
    leaf out-low-priority-cells {
      type oc-yang:counter64;
      description
        "Outgoing low priority cells towards the fabric from the
         integrated-circuit fabric subsystem block.";
    }
    uses pipeline-counters-common-high-low-packets;
  }

  grouping pipeline-counters-packet-host-interface-block-state {
    description
      "The IC host interface counters include packets/bytes in/out of the
       host interface subsystem and performance metrics for key functionality
       of this subsystem such as fragmented packet counts and hi/low priority
       packet counts";
    uses pipeline-packets-common;
    leaf fragment-punt-pkts {
      type oc-yang:counter64;
      description
        "The packets that were successfully punted to CPU due to egress MTU
         exceeded.";
    }
    uses pipeline-counters-common-high-low-packets;
  }

  grouping pipeline-drops-common {
    description
      "A common set of drop counters that apply to multiple drop sections.";
    leaf oversubscription {
      type oc-yang:counter64;
      description
        "Number of packets dropped due to oversubscription of the
         integrated-circuit subsystem block.";
    }
  }

  grouping pipeline-drops-common-high-low {
    description
      "A common set of drop counters for high and low priority.";
    leaf in-high-priority {
      type oc-yang:counter64;
      description
        "Incoming high priority drops towards this integrated-circuit
         subsystem block from the previous NPU sub-block or interface.";
    }
    leaf out-high-priority {
      type oc-yang:counter64;
      description
        "Outgoing high priority drops towards the fabric/interface from this
         integrated-circuit subsystem block.";
    }
    leaf in-low-priority {
      type oc-yang:counter64;
      description
        "Incoming low priority drops towards this integrated-circuit
         subsystem block from the previous NPU sub-block or interface.";
    }
    leaf out-low-priority {
      type oc-yang:counter64;
      description
        "Outgoing low priority drops towards the fabric/interface from this
         integrated-circuit subsystem block.";
    }
  }

  grouping pipeline-drop-packet-interface-block-state {
    description
      "Each drop counter will aggregate incoming and outgoing packets, and
       oversubscription drops that connect the IC to the external MAC or PHY.";
    uses pipeline-drops-common;
    leaf in-drops {
      type oc-yang:counter64;
      description
        "Incoming drops towards the integrated-circuit interface
         subsystem block from the interfaces due to any reason.";
    }
    leaf out-drops {
      type oc-yang:counter64;
      description
        "Outgoing drops towards the interfaces from the
         integrated-circuit interface subsystem block due to any reason.";
    }
  }

  grouping pipeline-drop-packet-lookup-block-state {
    description
      "The IC lookup subsystem drop counters track key functionality of this
       subsystem such as Oversubscription, no-route, no-label, no-NH, invalid-
       packets, forwarding-policy, incorrect-software, rate-limit, fragments,
       and firewall drops";
    uses pipeline-drops-common;
    leaf no-route {
      type oc-yang:counter64;
      description
        "Packets dropped due to no FIB entry for this ipv4 or ipv6 lookup.";
    }
    leaf no-label {
      type oc-yang:counter64;
      description
        "Packets dropped due to no FIB entry for this MPLS label.";
    }
    leaf no-nexthop {
      type oc-yang:counter64;
      description
        "Packets dropped due to no nexthop information - either the nexthop is
         not programmed, or there is an invalid nexthop, or there is no ARP
         information so the nexthop is in invalid state.";
    }
    leaf invalid-packet {
      type oc-yang:counter64;
      description
        "Packets dropped due to invalid packet format for ipv4, ipv6, or MPLS.";
    }
    leaf forwarding-policy {
      type oc-yang:counter64;
      description
        "Packets dropped due to either a filter applied as part of a forwarding
         policy or dropped due to a policy-based-routing policy lookup.";
    }
    leaf incorrect-software-state {
      type oc-yang:counter64;
      description
        "Packets dropped due to any incorrect or invalid software state of the
         forwarding structures during lookup.";
    }
    leaf rate-limit {
      type oc-yang:counter64;
      description
        "Packets dropped due to rate limiters - either user configured rate
         limiters or system rate limiters in the forwarding path.";
    }
    leaf fragment-total-drops {
      type oc-yang:counter64;
      description
        "Total number of packets dropped that could not be fragmented by NPU
         due to DF bit.";
    }
    leaf lookup-aggregate {
      type oc-yang:counter64;
      description
        "Packets dropped due to aggregate lookup drop counters - this counter
         is sometimes referred to as Normal Discards or
         ENQ_DISCARDED_PACKET_COUNTER.";
    }
    leaf acl-drops {
      type oc-yang:counter64;
      description
        "Packets dropped due to firewall or acl terms.";
    }
  }

  grouping pipeline-drop-packet-queueing-block-state {
    description
      "The IC queueing subsystem drop counters track key functionality of this
       subsystem such as oversubscription, memory-limit, incorrect-state, and
       loopback drops.";
    uses pipeline-drops-common;
    leaf memory-limit {
      type oc-yang:counter64;
      description
        "Packets dropped due to running out of the queue memory.";
    }
    leaf incorrect-state {
      type oc-yang:counter64;
      description
        "Packets dropped due to hardware of software incorrect state of VOQs,
         or fabric queues, or interface queues.";
    }
    leaf lookup-queue {
      type oc-yang:counter64;
      description
        "Packets dropped in either the lookup or recirculation path.";
    }
  }

  grouping pipeline-drop-packet-fabric-block-state {
    description
      "The IC fabric subsystem drop counters track key functionality of this
       subsystem such as oversubscription, lost-packets, high and low priority
       packet drops.";
    uses pipeline-drops-common;
    leaf lost-packets {
      type oc-yang:counter64;
      description
        "Fabric drops due to re-ordering, or due to packets arriving late, or
         due to some loss in the fabric.";
    }
    uses pipeline-drops-common-high-low;
    leaf fabric-aggregate {
      type oc-yang:counter64;
      description
        "Aggregate of fabric-in and fabric-out drops.";
    }
  }

  grouping pipeline-drop-packet-host-interface-block-state {
    description
      "The IC host interface drop counters track key funcitonality of this
       subsystem such as oversubscription, rate-limit, fragment, and
       hi/low priority drop counts";
    uses pipeline-drops-common;
    leaf rate-limit {
      type oc-yang:counter64;
      description
        "Packet drops due to the rate limit in the integrated-circuit host
         subsystem block.";
    }
    uses pipeline-drops-common-high-low;
    leaf fragment-punt {
      type oc-yang:counter64;
      description
        "The packets that were failed to punt to CPU due to policing rate.";
    }
    leaf host-aggregate {
      type oc-yang:counter64;
      description
        "Aggregate of all the drops in the host path.";
    }
  }

  grouping pipeline-errors-common {
    description
      "A common set of error counters that apply to multiple error sections.";
    leaf name {
      type string;
      description
        "Name of the interrupt, hardware error, or software error in the NPU.";
    }
    leaf count {
      type uint64;
      description
        "Total count of errors of this type.";
    }
    leaf threshold {
      type uint64;
      description
        "Number of errors before a recovery action is automatically
         taken by the system.";
    }
    leaf-list action {
      type enumeration {
        enum "LOG" {
          description
            "Log a descriptive message.";
        }
        enum "LINECARD_REBOOT" {
          description
            "The line card is brought offline and then back online.";
        }
        enum "LINECARD_OFFLINE" {
          description
            "The line card is brought offline.";
        }
        enum "NPU_RESET" {
          description
            "The NPU is brought offline and then back online.";
        }
        enum "NPU_OFFLINE" {
          description
            "The NPU is brought offline.";
        }
        enum "GET_DIAGNOSTIC_INFO" {
          description
            "Diagnostic data is gathered at the time of the problem.";
        }
        enum "ALARM" {
          description
            "An Alarm is raised";
        }
      }
      description
        "Error actions that are taken by the system - log, linecard reboot,
         linecard offline, NPU reset, NPU offline, gather diagnostic data,
         raise an alarm.";
    }
    leaf active {
      type boolean;
      description
        "The error is currently in an active state. When the system detects
         that the specified threshold is exceeded, this value should be set to
         true.";
      default "false";
      oc-ext:telemetry-on-change;
    }
    leaf level {
      type enumeration {
        enum "FATAL" {
          description
            "The Fatal error causes total packet loss";
        }
        enum "MAJOR" {
          description
            "The Major error causes persistent packet loss";
        }
        enum "MINOR" {
          description
            "The Minor error is an indication of some past problem, but now is
             corrected";
        }
        enum "INFORMATIONAL" {
          description
            "Some problem happened that is not packet loss affecting.";
        }
      }
      description
        "The severity of the error that is being recorded by the system. This
         value can be used by a consumer to determine the action when this error
         is recorded.";
    }
  }

  grouping pipeline-errors-packet-interface-block-state {
    description
      "Error counter will aggregate the errors that connect the IC to the
       external MAC or PHY. Each error should contain the name, count,
       last-occurrence, threshold, action, and severity level.";
    uses pipeline-errors-common;
  }

  grouping pipeline-errors-packet-lookup-block-state {
    description
      "The IC lookup subsystem error counters include the errors encountered by
       the lookup subsystem. Each error should contain the name, count,
       last-occurrence, threshold, action, and severity level.";
    uses pipeline-errors-common;
  }

  grouping pipeline-errors-packet-queueing-block-state {
    description
      "The IC queueing subsystem error counters include the errors encountered
       by the queueing subsystem. Each error should contain the name, count,
       last-occurrence, threshold, action, and severity level.";
    uses pipeline-errors-common;
  }

  grouping pipeline-errors-packet-fabric-block-state {
    description
      "The IC fabric subsystem error counters include the errors encountered by
       the fabric subsystem. Each error should contain the name, count,
       last-occurrence, threshold, action, and severity level.";
    uses pipeline-errors-common;
  }

  grouping pipeline-errors-packet-host-interface-block-state {
    description
      "The IC host interface error counters include the errors encountered by
       the host interface subsystem. Each error should contain the name, count,
       last-occurrence, threshold, action, and severity level.";
    uses pipeline-errors-common;
  }

  augment "/ncs:devices/ncs:template/ncs:ned-id/ncs:config/oc-platform:components/oc-platform:component/oc-platform:integrated-circuit" {
    description
      "Add operational state data that corresponds to sub-blocks of an integrated
       circuit (NPU, ASIC) to the platform model.";
    uses ncs_template_platform-pipeline-top;
  }
  augment "/ncs:devices/ncs:device/ncs:live-status/oc-platform:components/oc-platform:component/oc-platform:integrated-circuit" {
    description
      "Add operational state data that corresponds to sub-blocks of an integrated
       circuit (NPU, ASIC) to the platform model.";
    uses live_ncs_platform-pipeline-top {
      refine pipeline-counters {
        tailf:ncs-device-type "netconf";
        tailf:display-when "not(../../../../../ncs:module) or ../../../../../ncs:module[ncs:name='openconfig-platform-pipeline-counters'] or (../../../../../ncs:live-status-protocol[not(ncs:capability)]) or (../../../../../ncs:live-status-protocol/ncs:capability/ncs:module[.='openconfig-platform-pipeline-counters'])";
      }
    }
  }
  augment "/ncs:devices/ncs:device/ncs:config/oc-platform:components/oc-platform:component/oc-platform:integrated-circuit" {
    description
      "Add operational state data that corresponds to sub-blocks of an integrated
       circuit (NPU, ASIC) to the platform model.";
    uses platform-pipeline-top;
  }
}
