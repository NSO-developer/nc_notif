submodule openconfig-rib-bgp-table-attributes {
  // Generated by yanger -t ncs
  tailf:mount-id "oc-all-nc-1.0:oc-all-nc-1.0";

  belongs-to openconfig-rib-bgp {
    prefix oc-rib-bgp;
  }

  import openconfig-extensions {
    prefix oc-ext;
  }
  import openconfig-types {
    prefix oc-types;
  }
  import openconfig-rib-bgp-types {
    prefix oc-bgpribt;
  }
  import tailf-common {
    prefix tailf;
  }
  import tailf-ncs {
    prefix ncs;
  }

  organization
    "OpenConfig working group";
  contact
    "OpenConfig working group
     www.openconfig.net";
  description
    "This submodule contains common data definitions for data
     related to a RIB entry, or RIB table.";
  oc-ext:openconfig-version "0.8.1";

  revision 2022-06-06 {
    description
      "Revert IETF types in favor of oc-inet types";
    reference "0.8.1";
  }
  revision 2021-06-21 {
    description
      "Add L2VPN-EVPN BGP RIB Support";
    reference "0.8.0";
  }
  revision 2019-10-15 {
    description
      "Change imported segment-routing module.";
    reference "0.7.0";
  }
  revision 2019-04-25 {
    description
      "Update last-modified timestamp to be expressed as nanoseconds
       since the Unix epoch.";
    reference "0.6.0";
  }
  revision 2019-04-16 {
    description
      "Rename the top-level BGP RIB container's name
       to RIB.";
    reference "0.5.0";
  }
  revision 2019-02-27 {
    description
      "Remove top-level BGP RIB container, and update list
       names to be compatible with path compression.";
    reference "0.4.0";
  }
  revision 2018-11-21 {
    description
      "Add OpenConfig module metadata extensions.";
    reference "0.3.1";
  }
  revision 2016-10-17 {
    description
      "OpenConfig BGP RIB refactor";
    reference "0.3.0";
  }

  grouping ncs_template_bgp-common-route-annotations-state {
    description
      "Data definitions for flags and other information attached
       to routes in both LOC-RIB and Adj-RIB";
    leaf last-modified {
      type oc-types:ncs_template_timeticks64;
      description
        "Timestamp when this path was last modified.

         The value is the timestamp relative to
         the Unix Epoch (Jan 1, 1970 00:00:00 UTC).";
    }
    leaf valid-route {
      type string;
      description
        "Indicates that the route is considered valid by the
         local router";
    }
    leaf invalid-reason {
      type string;
      description
        "If the route is rejected as invalid, this indicates the
         reason.";
    }
  }

  grouping ncs_template_bgp-loc-rib-route-annotations-state {
    description
      "Data definitions for information attached to routes in the
       LOC-RIB";
  }

  grouping ncs_template_bgp-adj-rib-in-post-route-annotations-state {
    description
      "Data definitions for information attached to routes in the
       Adj-RIB-in post-policy table";
    leaf best-path {
      type string;
      description
        "Current path was selected as the best path.";
    }
  }

  grouping ncs_template_bgp-common-table-attrs-state {
    description
      "Common attributes attached to all routing tables";
  }

  grouping ncs_template_bgp-common-table-attrs-top {
    description
      "Operational state data for common attributes attached to
       all routing tables";
    // NCS drop config false container state
  }

  grouping ncs_rpc_notif_bgp-common-route-annotations-state {
    description
      "Data definitions for flags and other information attached
       to routes in both LOC-RIB and Adj-RIB";
    leaf last-modified {
      type oc-types:ncs_rpc_notif_timeticks64;
      description
        "Timestamp when this path was last modified.

         The value is the timestamp relative to
         the Unix Epoch (Jan 1, 1970 00:00:00 UTC).";
    }
    leaf valid-route {
      type boolean;
      description
        "Indicates that the route is considered valid by the
         local router";
    }
    leaf invalid-reason {
      type identityref {
        base oc-bgpribt:INVALID_ROUTE_REASON;
      }
      description
        "If the route is rejected as invalid, this indicates the
         reason.";
    }
  }

  grouping ncs_rpc_notif_bgp-loc-rib-route-annotations-state {
    description
      "Data definitions for information attached to routes in the
       LOC-RIB";
  }

  grouping ncs_rpc_notif_bgp-adj-rib-in-post-route-annotations-state {
    description
      "Data definitions for information attached to routes in the
       Adj-RIB-in post-policy table";
    leaf best-path {
      type boolean;
      description
        "Current path was selected as the best path.";
    }
  }

  grouping ncs_rpc_notif_bgp-common-table-attrs-state {
    description
      "Common attributes attached to all routing tables";
  }

  grouping ncs_rpc_notif_bgp-common-table-attrs-top {
    description
      "Operational state data for common attributes attached to
       all routing tables";
    container state {
      config false;
      description
        "Operational state data for data related to the entire
         LOC-RIB";
      uses ncs_rpc_notif_bgp-common-table-attrs-state;
    }
  }

  grouping live_ncs_bgp-common-route-annotations-state {
    description
      "Data definitions for flags and other information attached
       to routes in both LOC-RIB and Adj-RIB";
    leaf last-modified {
      type oc-types:live_ncs_timeticks64;
      description
        "Timestamp when this path was last modified.

         The value is the timestamp relative to
         the Unix Epoch (Jan 1, 1970 00:00:00 UTC).";
    }
    leaf valid-route {
      type boolean;
      description
        "Indicates that the route is considered valid by the
         local router";
    }
    leaf invalid-reason {
      type identityref {
        base oc-bgpribt:INVALID_ROUTE_REASON;
      }
      description
        "If the route is rejected as invalid, this indicates the
         reason.";
    }
  }

  grouping live_ncs_bgp-loc-rib-route-annotations-state {
    description
      "Data definitions for information attached to routes in the
       LOC-RIB";
  }

  grouping live_ncs_bgp-adj-rib-in-post-route-annotations-state {
    description
      "Data definitions for information attached to routes in the
       Adj-RIB-in post-policy table";
    leaf best-path {
      type boolean;
      description
        "Current path was selected as the best path.";
    }
  }

  grouping live_ncs_bgp-common-table-attrs-state {
    description
      "Common attributes attached to all routing tables";
  }

  grouping live_ncs_bgp-common-table-attrs-top {
    description
      "Operational state data for common attributes attached to
       all routing tables";
    container state {
      description
        "Operational state data for data related to the entire
         LOC-RIB";
      uses live_ncs_bgp-common-table-attrs-state;
    }
  }

  grouping bgp-common-route-annotations-state {
    description
      "Data definitions for flags and other information attached
       to routes in both LOC-RIB and Adj-RIB";
    leaf last-modified {
      type oc-types:timeticks64;
      description
        "Timestamp when this path was last modified.

         The value is the timestamp relative to
         the Unix Epoch (Jan 1, 1970 00:00:00 UTC).";
    }
    leaf valid-route {
      type boolean;
      description
        "Indicates that the route is considered valid by the
         local router";
    }
    leaf invalid-reason {
      type identityref {
        base oc-bgpribt:INVALID_ROUTE_REASON;
      }
      description
        "If the route is rejected as invalid, this indicates the
         reason.";
    }
  }

  grouping bgp-loc-rib-route-annotations-state {
    description
      "Data definitions for information attached to routes in the
       LOC-RIB";
  }

  grouping bgp-adj-rib-in-post-route-annotations-state {
    description
      "Data definitions for information attached to routes in the
       Adj-RIB-in post-policy table";
    leaf best-path {
      type boolean;
      description
        "Current path was selected as the best path.";
    }
  }

  grouping bgp-common-table-attrs-state {
    description
      "Common attributes attached to all routing tables";
  }

  grouping bgp-common-table-attrs-top {
    description
      "Operational state data for common attributes attached to
       all routing tables";
    // NCS drop config false container state
  }
}
