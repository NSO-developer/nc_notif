module openconfig-lacp {
  // Generated by yanger -t ncs
  tailf:mount-id "oc-all-nc-1.0:oc-all-nc-1.0";
  tailf:ncs-device-type "netconf";

  yang-version 1;
  namespace "http://openconfig.net/yang/lacp";
  prefix oc-lacp;

  import openconfig-interfaces {
    prefix oc-if;
  }
  import openconfig-yang-types {
    prefix oc-yang;
  }
  import openconfig-extensions {
    prefix oc-ext;
  }
  import openconfig-types {
    prefix oc-types;
  }
  import tailf-common {
    prefix tailf;
  }
  import tailf-ncs {
    prefix ncs;
  }

  organization
    "OpenConfig working group";
  contact
    "OpenConfig working group
     www.openconfig.net";
  description
    "This module describes configuration and operational state
     data for Link Aggregation Control Protocol (LACP) for
     managing aggregate interfaces.   It works in conjunction with
     the OpenConfig interfaces and aggregate interfaces models.";
  oc-ext:openconfig-version "1.2.0";

  revision 2021-07-20 {
    description
      "Add count of number of timeouts and time of the last timeout.";
    reference "1.2.0";
  }
  revision 2018-11-21 {
    description
      "Add OpenConfig module metadata extensions.";
    reference "1.1.1";
  }
  revision 2017-05-05 {
    description
      "Add member local and remote port num";
    reference "1.1.0";
  }
  revision 2016-05-26 {
    description
      "OpenConfig public release";
    reference "1.0.2";
  }
  oc-ext:regexp-posix;
  oc-ext:catalog-organization "openconfig";
  oc-ext:origin "openconfig";

  typedef ncs_template_lacp-activity-type {
    type string;
    description
      "Describes the LACP membership type, active or passive, of the
       interface in the aggregate";
    reference "IEEE 802.1AX-2008";
  }

  typedef ncs_template_lacp-timeout-type {
    type string;
    description
      "Type of timeout used, short or long, by LACP participants";
    reference "IEEE 802.1AX-2008";
  }

  typedef ncs_template_lacp-synchronization-type {
    type string;
    description
      "Indicates LACP synchronization state of participant";
    reference "IEEE 802.1AX-2008";
  }

  typedef ncs_template_lacp-period-type {
    type string;
    description
      "Defines the period options for the time between sending
       LACP messages";
    reference "IEEE 802.3ad";
  }

  typedef ncs_rpc_notif_lacp-activity-type {
    type enumeration {
      enum "ACTIVE" {
        description
          "Interface is an active member, i.e., will detect and
           maintain aggregates";
      }
      enum "PASSIVE" {
        description
          "Interface is a passive member, i.e., it participates
           with an active partner";
      }
    }
    description
      "Describes the LACP membership type, active or passive, of the
       interface in the aggregate";
    reference "IEEE 802.1AX-2008";
  }

  typedef ncs_rpc_notif_lacp-timeout-type {
    type enumeration {
      enum "LONG" {
        description
          "Participant wishes to use long timeouts to detect
           status of the aggregate, i.e., will expect less frequent
           transmissions. Long timeout is 90 seconds.";
      }
      enum "SHORT" {
        description
          "Participant wishes to use short timeouts, i.e., expects
           frequent transmissions to aggressively detect status
           changes. Short timeout is 3 seconds.";
      }
    }
    description
      "Type of timeout used, short or long, by LACP participants";
    reference "IEEE 802.1AX-2008";
  }

  typedef ncs_rpc_notif_lacp-synchronization-type {
    type enumeration {
      enum "IN_SYNC" {
        description
          "Participant is in sync with the system id and key
           transmitted";
      }
      enum "OUT_SYNC" {
        description
          "Participant is not in sync with the system id and key
           transmitted";
      }
    }
    description
      "Indicates LACP synchronization state of participant";
    reference "IEEE 802.1AX-2008";
  }

  typedef ncs_rpc_notif_lacp-period-type {
    type enumeration {
      enum "FAST" {
        description
          "Send LACP packets every second";
      }
      enum "SLOW" {
        description
          "Send LACP packets every 30 seconds";
      }
    }
    description
      "Defines the period options for the time between sending
       LACP messages";
    reference "IEEE 802.3ad";
  }

  typedef live_ncs_lacp-activity-type {
    type enumeration {
      enum "ACTIVE" {
        description
          "Interface is an active member, i.e., will detect and
           maintain aggregates";
      }
      enum "PASSIVE" {
        description
          "Interface is a passive member, i.e., it participates
           with an active partner";
      }
    }
    description
      "Describes the LACP membership type, active or passive, of the
       interface in the aggregate";
    reference "IEEE 802.1AX-2008";
  }

  typedef live_ncs_lacp-timeout-type {
    type enumeration {
      enum "LONG" {
        description
          "Participant wishes to use long timeouts to detect
           status of the aggregate, i.e., will expect less frequent
           transmissions. Long timeout is 90 seconds.";
      }
      enum "SHORT" {
        description
          "Participant wishes to use short timeouts, i.e., expects
           frequent transmissions to aggressively detect status
           changes. Short timeout is 3 seconds.";
      }
    }
    description
      "Type of timeout used, short or long, by LACP participants";
    reference "IEEE 802.1AX-2008";
  }

  typedef live_ncs_lacp-synchronization-type {
    type enumeration {
      enum "IN_SYNC" {
        description
          "Participant is in sync with the system id and key
           transmitted";
      }
      enum "OUT_SYNC" {
        description
          "Participant is not in sync with the system id and key
           transmitted";
      }
    }
    description
      "Indicates LACP synchronization state of participant";
    reference "IEEE 802.1AX-2008";
  }

  typedef live_ncs_lacp-period-type {
    type enumeration {
      enum "FAST" {
        description
          "Send LACP packets every second";
      }
      enum "SLOW" {
        description
          "Send LACP packets every 30 seconds";
      }
    }
    description
      "Defines the period options for the time between sending
       LACP messages";
    reference "IEEE 802.3ad";
  }

  typedef lacp-activity-type {
    type enumeration {
      enum "ACTIVE" {
        description
          "Interface is an active member, i.e., will detect and
           maintain aggregates";
      }
      enum "PASSIVE" {
        description
          "Interface is a passive member, i.e., it participates
           with an active partner";
      }
    }
    description
      "Describes the LACP membership type, active or passive, of the
       interface in the aggregate";
    reference "IEEE 802.1AX-2008";
  }

  typedef lacp-timeout-type {
    type enumeration {
      enum "LONG" {
        description
          "Participant wishes to use long timeouts to detect
           status of the aggregate, i.e., will expect less frequent
           transmissions. Long timeout is 90 seconds.";
      }
      enum "SHORT" {
        description
          "Participant wishes to use short timeouts, i.e., expects
           frequent transmissions to aggressively detect status
           changes. Short timeout is 3 seconds.";
      }
    }
    description
      "Type of timeout used, short or long, by LACP participants";
    reference "IEEE 802.1AX-2008";
  }

  typedef lacp-synchronization-type {
    type enumeration {
      enum "IN_SYNC" {
        description
          "Participant is in sync with the system id and key
           transmitted";
      }
      enum "OUT_SYNC" {
        description
          "Participant is not in sync with the system id and key
           transmitted";
      }
    }
    description
      "Indicates LACP synchronization state of participant";
    reference "IEEE 802.1AX-2008";
  }

  typedef lacp-period-type {
    type enumeration {
      enum "FAST" {
        description
          "Send LACP packets every second";
      }
      enum "SLOW" {
        description
          "Send LACP packets every 30 seconds";
      }
    }
    description
      "Defines the period options for the time between sending
       LACP messages";
    reference "IEEE 802.3ad";
  }

  grouping ncs_template_aggregation-lacp-members-config {
    description
      "Configuration data for lacp member interfaces";
  }

  grouping ncs_template_aggregation-lacp-members-state {
    description
      "Operational status data for the member interfaces";
    leaf interface {
      type oc-if:ncs_template_base-interface-ref;
      description
        "Reference to interface member of the LACP aggregate";
    }
    leaf activity {
      type ncs_template_lacp-activity-type;
      description
        "Indicates participant is active or passive";
    }
    leaf timeout {
      type ncs_template_lacp-timeout-type;
      description
        "The timeout type (short or long) used by the
         participant";
    }
    leaf synchronization {
      type ncs_template_lacp-synchronization-type;
      description
        "Indicates whether the participant is in-sync or
         out-of-sync";
    }
    leaf aggregatable {
      type string;
      description
        "A true value indicates that the participant will allow
         the link to be used as part of the aggregate. A false
         value indicates the link should be used as an individual
         link";
    }
    leaf collecting {
      type string;
      description
        "If true, the participant is collecting incoming frames
         on the link, otherwise false";
    }
    leaf distributing {
      type string;
      description
        "When true, the participant is distributing outgoing
         frames; when false, distribution is disabled";
    }
    leaf system-id {
      type oc-yang:ncs_template_mac-address;
      description
        "MAC address that defines the local system ID for the
         aggregate interface";
    }
    leaf oper-key {
      type string;
      description
        "Current operational value of the key for the aggregate
         interface";
    }
    leaf partner-id {
      type oc-yang:ncs_template_mac-address;
      description
        "MAC address representing the protocol partner's interface
         system ID";
    }
    leaf partner-key {
      type string;
      description
        "Operational value of the protocol partner's key";
    }
    leaf port-num {
      type string;
      description
        "Port number of the local (actor) aggregation member";
    }
    leaf partner-port-num {
      type string;
      description
        "Port number of the partner (remote) port for this member
         port";
    }
    leaf last-change {
      type oc-types:ncs_template_timeticks64;
      description
        "The timestamp indicates the absolute time of the last state
         change of a LACP timeout. The last state change of the LACP
         timeout is defined as what is reported as the operating state
         to the system. The state change is both a timeout event and
         when the timeout event is no longer active. The value is the
         timestamp in nanoseconds relative to the Unix Epoch
         (Jan 1, 1970 00:00:00 UTC).";
    }
  }

  grouping ncs_template_aggregation-lacp-members-statistics {
    description
      "LACP packet statistics for the member interfaces";
    container counters {
      description
        "LACP protocol counters";
      leaf lacp-in-pkts {
        type oc-yang:ncs_template_counter64;
        description
          "Number of LACPDUs received";
      }
      leaf lacp-out-pkts {
        type oc-yang:ncs_template_counter64;
        description
          "Number of LACPDUs transmitted";
      }
      leaf lacp-rx-errors {
        type oc-yang:ncs_template_counter64;
        description
          "Number of LACPDU receive packet errors";
      }
      leaf lacp-tx-errors {
        type oc-yang:ncs_template_counter64;
        description
          "Number of LACPDU transmit packet errors";
      }
      leaf lacp-unknown-errors {
        type oc-yang:ncs_template_counter64;
        description
          "Number of LACPDU unknown packet errors";
      }
      leaf lacp-errors {
        type oc-yang:ncs_template_counter64;
        description
          "Number of LACPDU illegal packet errors";
      }
      leaf lacp-timeout-transitions {
        type oc-yang:ncs_template_counter64;
        description
          "Number of times the LACP state has transitioned
           with a timeout since the time the device restarted
           or the interface was brought up, whichever is most
           recent. The last state change of the LACP timeout
           is defined as what is reported as the operating state
           to the system. The state change is both a timeout
           event and when the timeout event is no longer active.";
      }
    }
  }

  grouping ncs_template_aggregation-lacp-members-top {
    description
      "Top-level grouping for aggregate members list";
    // NCS drop config false container members
  }

  grouping ncs_template_lacp-interfaces-config {
    description
      "Configuration data for each LACP-enabled interface";
    leaf name {
      type oc-if:ncs_template_base-interface-ref;
      description
        "Reference to the interface on which LACP should be
         configured.   The type of the target interface must be
         ieee8023adLag";
    }
    leaf interval {
      type ncs_template_lacp-period-type;
      // NCS drop default statement
      description
        "Set the period between LACP messages -- uses
         the lacp-period-type enumeration.";
    }
    leaf lacp-mode {
      type ncs_template_lacp-activity-type;
      // NCS drop default statement
      description
        "ACTIVE is to initiate the transmission of LACP packets.
         PASSIVE is to wait for peer to initiate the transmission of
         LACP packets.";
    }
    leaf system-id-mac {
      type oc-yang:ncs_template_mac-address;
      description
        "The MAC address portion of the node's System ID. This is
         combined with the system priority to construct the 8-octet
         system-id";
    }
    uses ncs_template_aggregation-lacp-global-config;
  }

  grouping ncs_template_lacp-interfaces-state {
    description
      "Operational state data for each LACP-enabled interface";
  }

  grouping ncs_template_lacp-interfaces-top {
    description
      "Top-level grouping for LACP-enabled interfaces";
    container interfaces {
      description
        "Enclosing container for the list of LACP-enabled
         interfaces";
      list interface {
        // NCS patched for predictable order
        ordered-by user;
        key "name";
        description
          "List of aggregate interfaces managed by LACP";
        leaf name {
          type string;
          description
            "Reference to the list key";
        }
        container config {
          description
            "Configuration data for each LACP aggregate interface";
          uses ncs_template_lacp-interfaces-config;
        }
        // NCS drop config false container state
        uses ncs_template_aggregation-lacp-members-top;
      }
    }
  }

  grouping ncs_template_aggregation-lacp-global-config {
    description
      "Configuration data for LACP aggregate interfaces";
    leaf system-priority {
      type string;
      description
        "Sytem priority used by the node on this LAG interface.
         Lower value is higher priority for determining which node
         is the controlling system.";
    }
  }

  grouping ncs_template_aggregation-lacp-global-state {
    description
      "Operational data for LACP aggregate interfaces";
  }

  grouping ncs_template_aggregation-lacp-top {
    description
      "Top level configuration and state variable containers for
       LACP data";
    container lacp {
      description
        "Configuration and operational state data for LACP protocol
         operation on the aggregate interface";
      container config {
        description
          "Configuration data for LACP";
        uses ncs_template_aggregation-lacp-global-config;
      }
      // NCS drop config false container state
      uses ncs_template_lacp-interfaces-top;
    }
  }

  grouping ncs_rpc_notif_aggregation-lacp-members-config {
    description
      "Configuration data for lacp member interfaces";
  }

  grouping ncs_rpc_notif_aggregation-lacp-members-state {
    description
      "Operational status data for the member interfaces";
    leaf interface {
      type oc-if:ncs_rpc_notif_base-interface-ref;
      description
        "Reference to interface member of the LACP aggregate";
    }
    leaf activity {
      type ncs_rpc_notif_lacp-activity-type;
      description
        "Indicates participant is active or passive";
    }
    leaf timeout {
      type ncs_rpc_notif_lacp-timeout-type;
      description
        "The timeout type (short or long) used by the
         participant";
    }
    leaf synchronization {
      type ncs_rpc_notif_lacp-synchronization-type;
      description
        "Indicates whether the participant is in-sync or
         out-of-sync";
    }
    leaf aggregatable {
      type boolean;
      description
        "A true value indicates that the participant will allow
         the link to be used as part of the aggregate. A false
         value indicates the link should be used as an individual
         link";
    }
    leaf collecting {
      type boolean;
      description
        "If true, the participant is collecting incoming frames
         on the link, otherwise false";
    }
    leaf distributing {
      type boolean;
      description
        "When true, the participant is distributing outgoing
         frames; when false, distribution is disabled";
    }
    leaf system-id {
      type oc-yang:ncs_rpc_notif_mac-address;
      description
        "MAC address that defines the local system ID for the
         aggregate interface";
    }
    leaf oper-key {
      type uint16;
      description
        "Current operational value of the key for the aggregate
         interface";
    }
    leaf partner-id {
      type oc-yang:ncs_rpc_notif_mac-address;
      description
        "MAC address representing the protocol partner's interface
         system ID";
    }
    leaf partner-key {
      type uint16;
      description
        "Operational value of the protocol partner's key";
    }
    leaf port-num {
      type uint16;
      description
        "Port number of the local (actor) aggregation member";
    }
    leaf partner-port-num {
      type uint16;
      description
        "Port number of the partner (remote) port for this member
         port";
    }
    leaf last-change {
      type oc-types:ncs_rpc_notif_timeticks64;
      description
        "The timestamp indicates the absolute time of the last state
         change of a LACP timeout. The last state change of the LACP
         timeout is defined as what is reported as the operating state
         to the system. The state change is both a timeout event and
         when the timeout event is no longer active. The value is the
         timestamp in nanoseconds relative to the Unix Epoch
         (Jan 1, 1970 00:00:00 UTC).";
    }
  }

  grouping ncs_rpc_notif_aggregation-lacp-members-statistics {
    description
      "LACP packet statistics for the member interfaces";
    container counters {
      description
        "LACP protocol counters";
      leaf lacp-in-pkts {
        type oc-yang:ncs_rpc_notif_counter64;
        description
          "Number of LACPDUs received";
      }
      leaf lacp-out-pkts {
        type oc-yang:ncs_rpc_notif_counter64;
        description
          "Number of LACPDUs transmitted";
      }
      leaf lacp-rx-errors {
        type oc-yang:ncs_rpc_notif_counter64;
        description
          "Number of LACPDU receive packet errors";
      }
      leaf lacp-tx-errors {
        type oc-yang:ncs_rpc_notif_counter64;
        description
          "Number of LACPDU transmit packet errors";
      }
      leaf lacp-unknown-errors {
        type oc-yang:ncs_rpc_notif_counter64;
        description
          "Number of LACPDU unknown packet errors";
      }
      leaf lacp-errors {
        type oc-yang:ncs_rpc_notif_counter64;
        description
          "Number of LACPDU illegal packet errors";
      }
      leaf lacp-timeout-transitions {
        type oc-yang:ncs_rpc_notif_counter64;
        description
          "Number of times the LACP state has transitioned
           with a timeout since the time the device restarted
           or the interface was brought up, whichever is most
           recent. The last state change of the LACP timeout
           is defined as what is reported as the operating state
           to the system. The state change is both a timeout
           event and when the timeout event is no longer active.";
      }
    }
  }

  grouping ncs_rpc_notif_aggregation-lacp-members-top {
    description
      "Top-level grouping for aggregate members list";
    container members {
      config false;
      description
        "Enclosing container for the list of members interfaces of
         the aggregate. This list is considered operational state
         only so is labeled config false and has no config container";
      list member {
        key "interface";
        description
          "List of member interfaces and their associated status for
           a LACP-controlled aggregate interface.  Member list is not
           configurable here -- each interface indicates items
           its participation in the LAG.";
        leaf interface {
          type leafref {
            path "../state/interface";
          }
          description
            "Reference to aggregate member interface";
        }
        container state {
          config false;
          description
            "Operational state data for aggregate members";
          uses ncs_rpc_notif_aggregation-lacp-members-state;
          uses ncs_rpc_notif_aggregation-lacp-members-statistics;
        }
      }
    }
  }

  grouping ncs_rpc_notif_lacp-interfaces-config {
    description
      "Configuration data for each LACP-enabled interface";
    leaf name {
      type oc-if:ncs_rpc_notif_base-interface-ref;
      description
        "Reference to the interface on which LACP should be
         configured.   The type of the target interface must be
         ieee8023adLag";
    }
    leaf interval {
      type ncs_rpc_notif_lacp-period-type;
      default "SLOW";
      description
        "Set the period between LACP messages -- uses
         the lacp-period-type enumeration.";
    }
    leaf lacp-mode {
      type ncs_rpc_notif_lacp-activity-type;
      default "ACTIVE";
      description
        "ACTIVE is to initiate the transmission of LACP packets.
         PASSIVE is to wait for peer to initiate the transmission of
         LACP packets.";
    }
    leaf system-id-mac {
      type oc-yang:ncs_rpc_notif_mac-address;
      description
        "The MAC address portion of the node's System ID. This is
         combined with the system priority to construct the 8-octet
         system-id";
    }
    uses ncs_rpc_notif_aggregation-lacp-global-config;
  }

  grouping ncs_rpc_notif_lacp-interfaces-state {
    description
      "Operational state data for each LACP-enabled interface";
  }

  grouping ncs_rpc_notif_lacp-interfaces-top {
    description
      "Top-level grouping for LACP-enabled interfaces";
    container interfaces {
      description
        "Enclosing container for the list of LACP-enabled
         interfaces";
      list interface {
        key "name";
        description
          "List of aggregate interfaces managed by LACP";
        leaf name {
          type leafref {
            path "../config/name";
          }
          description
            "Reference to the list key";
        }
        container config {
          description
            "Configuration data for each LACP aggregate interface";
          uses ncs_rpc_notif_lacp-interfaces-config;
        }
        container state {
          config false;
          description
            "Operational state data for each LACP aggregate
             interface";
          uses ncs_rpc_notif_lacp-interfaces-config;
          uses ncs_rpc_notif_lacp-interfaces-state;
        }
        uses ncs_rpc_notif_aggregation-lacp-members-top;
      }
    }
  }

  grouping ncs_rpc_notif_aggregation-lacp-global-config {
    description
      "Configuration data for LACP aggregate interfaces";
    leaf system-priority {
      type uint16;
      description
        "Sytem priority used by the node on this LAG interface.
         Lower value is higher priority for determining which node
         is the controlling system.";
    }
  }

  grouping ncs_rpc_notif_aggregation-lacp-global-state {
    description
      "Operational data for LACP aggregate interfaces";
  }

  grouping ncs_rpc_notif_aggregation-lacp-top {
    description
      "Top level configuration and state variable containers for
       LACP data";
    container lacp {
      description
        "Configuration and operational state data for LACP protocol
         operation on the aggregate interface";
      container config {
        description
          "Configuration data for LACP";
        uses ncs_rpc_notif_aggregation-lacp-global-config;
      }
      container state {
        config false;
        description
          "Operational state data for LACP";
        uses ncs_rpc_notif_aggregation-lacp-global-config;
        uses ncs_rpc_notif_aggregation-lacp-global-state;
      }
      uses ncs_rpc_notif_lacp-interfaces-top;
    }
  }

  grouping live_ncs_aggregation-lacp-members-config {
    description
      "Configuration data for lacp member interfaces";
  }

  grouping live_ncs_aggregation-lacp-members-state {
    description
      "Operational status data for the member interfaces";
    leaf interface {
      type oc-if:live_ncs_base-interface-ref;
      description
        "Reference to interface member of the LACP aggregate";
    }
    leaf activity {
      type live_ncs_lacp-activity-type;
      description
        "Indicates participant is active or passive";
    }
    leaf timeout {
      type live_ncs_lacp-timeout-type;
      description
        "The timeout type (short or long) used by the
         participant";
    }
    leaf synchronization {
      type live_ncs_lacp-synchronization-type;
      description
        "Indicates whether the participant is in-sync or
         out-of-sync";
    }
    leaf aggregatable {
      type boolean;
      description
        "A true value indicates that the participant will allow
         the link to be used as part of the aggregate. A false
         value indicates the link should be used as an individual
         link";
    }
    leaf collecting {
      type boolean;
      description
        "If true, the participant is collecting incoming frames
         on the link, otherwise false";
    }
    leaf distributing {
      type boolean;
      description
        "When true, the participant is distributing outgoing
         frames; when false, distribution is disabled";
    }
    leaf system-id {
      type oc-yang:live_ncs_mac-address;
      description
        "MAC address that defines the local system ID for the
         aggregate interface";
    }
    leaf oper-key {
      type uint16;
      description
        "Current operational value of the key for the aggregate
         interface";
    }
    leaf partner-id {
      type oc-yang:live_ncs_mac-address;
      description
        "MAC address representing the protocol partner's interface
         system ID";
    }
    leaf partner-key {
      type uint16;
      description
        "Operational value of the protocol partner's key";
    }
    leaf port-num {
      type uint16;
      description
        "Port number of the local (actor) aggregation member";
    }
    leaf partner-port-num {
      type uint16;
      description
        "Port number of the partner (remote) port for this member
         port";
    }
    leaf last-change {
      type oc-types:live_ncs_timeticks64;
      description
        "The timestamp indicates the absolute time of the last state
         change of a LACP timeout. The last state change of the LACP
         timeout is defined as what is reported as the operating state
         to the system. The state change is both a timeout event and
         when the timeout event is no longer active. The value is the
         timestamp in nanoseconds relative to the Unix Epoch
         (Jan 1, 1970 00:00:00 UTC).";
    }
  }

  grouping live_ncs_aggregation-lacp-members-statistics {
    description
      "LACP packet statistics for the member interfaces";
    container counters {
      description
        "LACP protocol counters";
      leaf lacp-in-pkts {
        type oc-yang:live_ncs_counter64;
        description
          "Number of LACPDUs received";
      }
      leaf lacp-out-pkts {
        type oc-yang:live_ncs_counter64;
        description
          "Number of LACPDUs transmitted";
      }
      leaf lacp-rx-errors {
        type oc-yang:live_ncs_counter64;
        description
          "Number of LACPDU receive packet errors";
      }
      leaf lacp-tx-errors {
        type oc-yang:live_ncs_counter64;
        description
          "Number of LACPDU transmit packet errors";
      }
      leaf lacp-unknown-errors {
        type oc-yang:live_ncs_counter64;
        description
          "Number of LACPDU unknown packet errors";
      }
      leaf lacp-errors {
        type oc-yang:live_ncs_counter64;
        description
          "Number of LACPDU illegal packet errors";
      }
      leaf lacp-timeout-transitions {
        type oc-yang:live_ncs_counter64;
        description
          "Number of times the LACP state has transitioned
           with a timeout since the time the device restarted
           or the interface was brought up, whichever is most
           recent. The last state change of the LACP timeout
           is defined as what is reported as the operating state
           to the system. The state change is both a timeout
           event and when the timeout event is no longer active.";
      }
    }
  }

  grouping live_ncs_aggregation-lacp-members-top {
    description
      "Top-level grouping for aggregate members list";
    container members {
      description
        "Enclosing container for the list of members interfaces of
         the aggregate. This list is considered operational state
         only so is labeled config false and has no config container";
      list member {
        key "interface";
        description
          "List of member interfaces and their associated status for
           a LACP-controlled aggregate interface.  Member list is not
           configurable here -- each interface indicates items
           its participation in the LAG.";
        leaf interface {
          type leafref {
            path "../state/interface";
          }
          description
            "Reference to aggregate member interface";
        }
        container state {
          description
            "Operational state data for aggregate members";
          uses live_ncs_aggregation-lacp-members-state;
          uses live_ncs_aggregation-lacp-members-statistics;
        }
      }
    }
  }

  grouping live_ncs_lacp-interfaces-config {
    description
      "Configuration data for each LACP-enabled interface";
    leaf name {
      type oc-if:live_ncs_base-interface-ref;
      description
        "Reference to the interface on which LACP should be
         configured.   The type of the target interface must be
         ieee8023adLag";
    }
    leaf interval {
      type live_ncs_lacp-period-type;
      // NCS drop default statement
      description
        "Set the period between LACP messages -- uses
         the lacp-period-type enumeration.";
    }
    leaf lacp-mode {
      type live_ncs_lacp-activity-type;
      // NCS drop default statement
      description
        "ACTIVE is to initiate the transmission of LACP packets.
         PASSIVE is to wait for peer to initiate the transmission of
         LACP packets.";
    }
    leaf system-id-mac {
      type oc-yang:live_ncs_mac-address;
      description
        "The MAC address portion of the node's System ID. This is
         combined with the system priority to construct the 8-octet
         system-id";
    }
    uses live_ncs_aggregation-lacp-global-config;
  }

  grouping live_ncs_lacp-interfaces-state {
    description
      "Operational state data for each LACP-enabled interface";
  }

  grouping live_ncs_lacp-interfaces-top {
    description
      "Top-level grouping for LACP-enabled interfaces";
    container interfaces {
      description
        "Enclosing container for the list of LACP-enabled
         interfaces";
      list interface {
        key "name";
        description
          "List of aggregate interfaces managed by LACP";
        leaf name {
          type leafref {
            path "../config/name";
          }
          description
            "Reference to the list key";
        }
        container config {
          description
            "Configuration data for each LACP aggregate interface";
          uses live_ncs_lacp-interfaces-config;
        }
        container state {
          description
            "Operational state data for each LACP aggregate
             interface";
          uses live_ncs_lacp-interfaces-config;
          uses live_ncs_lacp-interfaces-state;
        }
        uses live_ncs_aggregation-lacp-members-top;
      }
    }
  }

  grouping live_ncs_aggregation-lacp-global-config {
    description
      "Configuration data for LACP aggregate interfaces";
    leaf system-priority {
      type uint16;
      description
        "Sytem priority used by the node on this LAG interface.
         Lower value is higher priority for determining which node
         is the controlling system.";
    }
  }

  grouping live_ncs_aggregation-lacp-global-state {
    description
      "Operational data for LACP aggregate interfaces";
  }

  grouping live_ncs_aggregation-lacp-top {
    description
      "Top level configuration and state variable containers for
       LACP data";
    container lacp {
      description
        "Configuration and operational state data for LACP protocol
         operation on the aggregate interface";
      container config {
        description
          "Configuration data for LACP";
        uses live_ncs_aggregation-lacp-global-config;
      }
      container state {
        description
          "Operational state data for LACP";
        uses live_ncs_aggregation-lacp-global-config;
        uses live_ncs_aggregation-lacp-global-state;
      }
      uses live_ncs_lacp-interfaces-top;
    }
  }

  grouping aggregation-lacp-members-config {
    description
      "Configuration data for lacp member interfaces";
  }

  grouping aggregation-lacp-members-state {
    description
      "Operational status data for the member interfaces";
    leaf interface {
      type oc-if:base-interface-ref;
      description
        "Reference to interface member of the LACP aggregate";
    }
    leaf activity {
      type lacp-activity-type;
      description
        "Indicates participant is active or passive";
    }
    leaf timeout {
      type lacp-timeout-type;
      description
        "The timeout type (short or long) used by the
         participant";
    }
    leaf synchronization {
      type lacp-synchronization-type;
      description
        "Indicates whether the participant is in-sync or
         out-of-sync";
    }
    leaf aggregatable {
      type boolean;
      description
        "A true value indicates that the participant will allow
         the link to be used as part of the aggregate. A false
         value indicates the link should be used as an individual
         link";
    }
    leaf collecting {
      type boolean;
      description
        "If true, the participant is collecting incoming frames
         on the link, otherwise false";
    }
    leaf distributing {
      type boolean;
      description
        "When true, the participant is distributing outgoing
         frames; when false, distribution is disabled";
    }
    leaf system-id {
      type oc-yang:mac-address;
      description
        "MAC address that defines the local system ID for the
         aggregate interface";
    }
    leaf oper-key {
      type uint16;
      description
        "Current operational value of the key for the aggregate
         interface";
    }
    leaf partner-id {
      type oc-yang:mac-address;
      description
        "MAC address representing the protocol partner's interface
         system ID";
    }
    leaf partner-key {
      type uint16;
      description
        "Operational value of the protocol partner's key";
    }
    leaf port-num {
      type uint16;
      description
        "Port number of the local (actor) aggregation member";
    }
    leaf partner-port-num {
      type uint16;
      description
        "Port number of the partner (remote) port for this member
         port";
    }
    leaf last-change {
      type oc-types:timeticks64;
      description
        "The timestamp indicates the absolute time of the last state
         change of a LACP timeout. The last state change of the LACP
         timeout is defined as what is reported as the operating state
         to the system. The state change is both a timeout event and
         when the timeout event is no longer active. The value is the
         timestamp in nanoseconds relative to the Unix Epoch
         (Jan 1, 1970 00:00:00 UTC).";
    }
  }

  grouping aggregation-lacp-members-statistics {
    description
      "LACP packet statistics for the member interfaces";
    container counters {
      description
        "LACP protocol counters";
      leaf lacp-in-pkts {
        type oc-yang:counter64;
        description
          "Number of LACPDUs received";
      }
      leaf lacp-out-pkts {
        type oc-yang:counter64;
        description
          "Number of LACPDUs transmitted";
      }
      leaf lacp-rx-errors {
        type oc-yang:counter64;
        description
          "Number of LACPDU receive packet errors";
      }
      leaf lacp-tx-errors {
        type oc-yang:counter64;
        description
          "Number of LACPDU transmit packet errors";
      }
      leaf lacp-unknown-errors {
        type oc-yang:counter64;
        description
          "Number of LACPDU unknown packet errors";
      }
      leaf lacp-errors {
        type oc-yang:counter64;
        description
          "Number of LACPDU illegal packet errors";
      }
      leaf lacp-timeout-transitions {
        type oc-yang:counter64;
        description
          "Number of times the LACP state has transitioned
           with a timeout since the time the device restarted
           or the interface was brought up, whichever is most
           recent. The last state change of the LACP timeout
           is defined as what is reported as the operating state
           to the system. The state change is both a timeout
           event and when the timeout event is no longer active.";
      }
    }
  }

  grouping aggregation-lacp-members-top {
    description
      "Top-level grouping for aggregate members list";
    // NCS drop config false container members
  }

  grouping lacp-interfaces-config {
    description
      "Configuration data for each LACP-enabled interface";
    leaf name {
      type oc-if:base-interface-ref;
      description
        "Reference to the interface on which LACP should be
         configured.   The type of the target interface must be
         ieee8023adLag";
    }
    leaf interval {
      type lacp-period-type;
      default "SLOW";
      description
        "Set the period between LACP messages -- uses
         the lacp-period-type enumeration.";
    }
    leaf lacp-mode {
      type lacp-activity-type;
      default "ACTIVE";
      description
        "ACTIVE is to initiate the transmission of LACP packets.
         PASSIVE is to wait for peer to initiate the transmission of
         LACP packets.";
    }
    leaf system-id-mac {
      type oc-yang:mac-address;
      description
        "The MAC address portion of the node's System ID. This is
         combined with the system priority to construct the 8-octet
         system-id";
    }
    uses aggregation-lacp-global-config;
  }

  grouping lacp-interfaces-state {
    description
      "Operational state data for each LACP-enabled interface";
  }

  grouping lacp-interfaces-top {
    description
      "Top-level grouping for LACP-enabled interfaces";
    container interfaces {
      description
        "Enclosing container for the list of LACP-enabled
         interfaces";
      list interface {
        key "name";
        description
          "List of aggregate interfaces managed by LACP";
        leaf name {
          type leafref {
            path "../config/name";
          }
          description
            "Reference to the list key";
        }
        container config {
          description
            "Configuration data for each LACP aggregate interface";
          uses lacp-interfaces-config;
        }
        // NCS drop config false container state
        uses aggregation-lacp-members-top;
      }
    }
  }

  grouping aggregation-lacp-global-config {
    description
      "Configuration data for LACP aggregate interfaces";
    leaf system-priority {
      type uint16;
      description
        "Sytem priority used by the node on this LAG interface.
         Lower value is higher priority for determining which node
         is the controlling system.";
    }
  }

  grouping aggregation-lacp-global-state {
    description
      "Operational data for LACP aggregate interfaces";
  }

  grouping aggregation-lacp-top {
    description
      "Top level configuration and state variable containers for
       LACP data";
    container lacp {
      description
        "Configuration and operational state data for LACP protocol
         operation on the aggregate interface";
      container config {
        description
          "Configuration data for LACP";
        uses aggregation-lacp-global-config;
      }
      // NCS drop config false container state
      uses lacp-interfaces-top;
    }
  }

  augment "/ncs:devices/ncs:device/ncs:config" {
    uses aggregation-lacp-top {
      refine lacp {
        tailf:ncs-device-type "netconf";
        tailf:display-when "not(../../ncs:module) or ../../ncs:module[ncs:name='openconfig-lacp']";
      }
    }
  }
  augment "/ncs:devices/ncs:device/ncs:live-status" {
    uses live_ncs_aggregation-lacp-top {
      refine lacp {
        tailf:ncs-device-type "netconf";
        tailf:display-when "not(../../ncs:module) or ../../ncs:module[ncs:name='openconfig-lacp'] or (../../ncs:live-status-protocol[not(ncs:capability)]) or (../../ncs:live-status-protocol/ncs:capability/ncs:module[.='openconfig-lacp'])";
      }
    }
  }
  augment "/ncs:devices/ncs:template/ncs:ned-id/ncs:config" {
    uses ncs_template_aggregation-lacp-top;
  }
}
