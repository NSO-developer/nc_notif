module openconfig-platform-controller-card {
  // Generated by yanger -t ncs
  tailf:mount-id "oc-all-nc-1.0:oc-all-nc-1.0";
  tailf:ncs-device-type "netconf";

  yang-version 1;
  namespace "http://openconfig.net/yang/platform/controller-card";
  prefix oc-ctrl-card;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines data related to CONTROLLER_CARD components in
     the openconfig-platform model";
  oc-ext:openconfig-version "0.1.0";

  revision 2022-07-28 {
    description
      "Initial revision";
    reference "0.1.0";
  }
  oc-ext:catalog-organization "openconfig";
  oc-ext:origin "openconfig";

  grouping ncs_template_controller-card-config {
    description
      "Configuration data for controller card components";
    uses oc-platform:ncs_template_component-power-management;
  }

  grouping ncs_rpc_notif_controller-card-config {
    description
      "Configuration data for controller card components";
    uses oc-platform:ncs_rpc_notif_component-power-management;
  }

  grouping live_ncs_controller-card-config {
    description
      "Configuration data for controller card components";
    uses oc-platform:live_ncs_component-power-management;
  }

  grouping controller-card-config {
    description
      "Configuration data for controller card components";
    uses oc-platform:component-power-management;
  }

  augment "/ncs:devices/ncs:template/ncs:ned-id/ncs:config/oc-platform:components/oc-platform:component/oc-platform:controller-card/oc-platform:config" {
    description
      "Adding controller card data to physical inventory. This subtree
       is only valid when the type of the component is CONTROLLER_CARD.";
    uses ncs_template_controller-card-config;
  }
  augment "/ncs:devices/ncs:device/ncs:live-status/oc-platform:components/oc-platform:component/oc-platform:controller-card/oc-platform:config" {
    description
      "Adding controller card data to physical inventory. This subtree
       is only valid when the type of the component is CONTROLLER_CARD.";
    uses live_ncs_controller-card-config {
      refine power-admin-state {
        tailf:ncs-device-type "netconf";
        tailf:display-when "not(../../../../../../ncs:module) or ../../../../../../ncs:module[ncs:name='openconfig-platform-controller-card'] or (../../../../../../ncs:live-status-protocol[not(ncs:capability)]) or (../../../../../../ncs:live-status-protocol/ncs:capability/ncs:module[.='openconfig-platform-controller-card'])";
      }
    }
  }
  augment "/ncs:devices/ncs:device/ncs:config/oc-platform:components/oc-platform:component/oc-platform:controller-card/oc-platform:config" {
    description
      "Adding controller card data to physical inventory. This subtree
       is only valid when the type of the component is CONTROLLER_CARD.";
    uses controller-card-config {
      refine power-admin-state {
        tailf:ncs-device-type "netconf";
        tailf:display-when "not(../../../../../../ncs:module) or ../../../../../../ncs:module[ncs:name='openconfig-platform-controller-card']";
      }
    }
  }
  augment "/ncs:devices/ncs:device/ncs:live-status/oc-platform:components/oc-platform:component/oc-platform:controller-card/oc-platform:state" {
    description
      "Adding controller card data to physical inventory. This subtree
       is only valid when the type of the component is CONTROLLER_CARD.";
    uses live_ncs_controller-card-config {
      refine power-admin-state {
        tailf:ncs-device-type "netconf";
        tailf:display-when "not(../../../../../../ncs:module) or ../../../../../../ncs:module[ncs:name='openconfig-platform-controller-card'] or (../../../../../../ncs:live-status-protocol[not(ncs:capability)]) or (../../../../../../ncs:live-status-protocol/ncs:capability/ncs:module[.='openconfig-platform-controller-card'])";
      }
    }
  }
}
