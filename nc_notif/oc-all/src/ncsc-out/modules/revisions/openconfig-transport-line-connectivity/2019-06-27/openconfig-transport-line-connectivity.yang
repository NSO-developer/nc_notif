module openconfig-transport-line-connectivity {
  // Generated by yanger -t ncs
  tailf:mount-id "oc-all-nc-1.0:oc-all-nc-1.0";
  tailf:ncs-device-type "netconf";

  yang-version 1;
  namespace "http://openconfig.net/yang/openconfig-transport-line-connectivity";
  prefix oc-line-connect;

  import openconfig-extensions {
    prefix oc-ext;
  }
  import openconfig-transport-types {
    prefix oc-opt-types;
  }
  import tailf-common {
    prefix tailf;
  }
  import tailf-ncs {
    prefix ncs;
  }

  organization
    "OpenConfig working group";
  contact
    "OpenConfig working group
      www.openconfig.net";
  description
    "This model describes the device-level connectivity
     (e.g., internal port-to-port) for optical transport line
     system elements such as wavelength routers (ROADMs) and
     amplifiers. All connections are uni-directional. Note that
     this model explicitly does not intend to model or provide
     a path to any higher layer topology modeling and is only
     for modeling internal links";
  oc-ext:openconfig-version "0.1.0";

  revision 2019-06-27 {
    description
      "Initial revision";
    reference "0.1.0";
  }
  oc-ext:regexp-posix;
  oc-ext:catalog-organization "openconfig";
  oc-ext:origin "openconfig";

  grouping ncs_template_connection-state {
    description
      "Operational state data for connections";
  }

  grouping ncs_template_connection-config {
    description
      "Configuration data for line system connections";
    leaf index {
      type string;
      description
        "Index for the defined connection";
    }
    leaf source {
      type string;
      description
        "The user supplied name of the source port of the connection
         within the system. If the port is within the device, the
         string should reflect the name of the port as it appears in
         the components model. If the port is not represented in the
         components model (e.g., a port on a passive chassis), the
         string should reflect the system assigned name of the port.
         If the source port is not within the device, then an
         identityref of EXTERNAL should be specified.";
    }
    leaf dest {
      type string;
      description
        "The user supplied name of the destination port of the connection
         within the system. If the port is within the device, the string
         should reflect the name of the port as it appears in the
         components model. If the port is not represented in the components
         model (e.g., a port on a passive chassis), the string should
         reflect the system assigned name of the port. If the destination
         port is not within the device, then an identityref of EXTERNAL
         should be specified.";
    }
    leaf fiber-type {
      description
        "The type of fiber jumper used for the connection.";
      type string;
    }
  }

  grouping ncs_template_line-connectivity-top {
    description
      "Top level grouping for transport line connectivity data";
    container connections {
      description
        "Enclosing container for line system connections list";
      list connection {
        // NCS patched for predictable order
        ordered-by user;
        key "index";
        description
          "List of line system connections";
        leaf index {
          type string;
          description
            "Reference to index number of the connection";
        }
        container config {
          description
            "Configuration data";
          uses ncs_template_connection-config;
        }
        // NCS drop config false container state
      }
    }
  }

  grouping ncs_rpc_notif_connection-state {
    description
      "Operational state data for connections";
  }

  grouping ncs_rpc_notif_connection-config {
    description
      "Configuration data for line system connections";
    leaf index {
      type uint32;
      description
        "Index for the defined connection";
    }
    leaf source {
      type union {
        type string;
        type identityref {
          base PORT_CONNECTION_TYPE;
        }
      }
      description
        "The user supplied name of the source port of the connection
         within the system. If the port is within the device, the
         string should reflect the name of the port as it appears in
         the components model. If the port is not represented in the
         components model (e.g., a port on a passive chassis), the
         string should reflect the system assigned name of the port.
         If the source port is not within the device, then an
         identityref of EXTERNAL should be specified.";
    }
    leaf dest {
      type union {
        type string;
        type identityref {
          base PORT_CONNECTION_TYPE;
        }
      }
      description
        "The user supplied name of the destination port of the connection
         within the system. If the port is within the device, the string
         should reflect the name of the port as it appears in the
         components model. If the port is not represented in the components
         model (e.g., a port on a passive chassis), the string should
         reflect the system assigned name of the port. If the destination
         port is not within the device, then an identityref of EXTERNAL
         should be specified.";
    }
    leaf fiber-type {
      description
        "The type of fiber jumper used for the connection.";
      type identityref {
        base oc-opt-types:FIBER_JUMPER_TYPE;
      }
    }
  }

  grouping ncs_rpc_notif_line-connectivity-top {
    description
      "Top level grouping for transport line connectivity data";
    container connections {
      description
        "Enclosing container for line system connections list";
      list connection {
        key "index";
        description
          "List of line system connections";
        leaf index {
          type leafref {
            path "../config/index";
          }
          description
            "Reference to index number of the connection";
        }
        container config {
          description
            "Configuration data";
          uses ncs_rpc_notif_connection-config;
        }
        container state {
          config false;
          description
            "Operational state data";
          uses ncs_rpc_notif_connection-config;
          uses ncs_rpc_notif_connection-state;
        }
      }
    }
  }

  grouping live_ncs_connection-state {
    description
      "Operational state data for connections";
  }

  grouping live_ncs_connection-config {
    description
      "Configuration data for line system connections";
    leaf index {
      type uint32;
      description
        "Index for the defined connection";
    }
    leaf source {
      type union {
        type string;
        type identityref {
          base PORT_CONNECTION_TYPE;
        }
      }
      description
        "The user supplied name of the source port of the connection
         within the system. If the port is within the device, the
         string should reflect the name of the port as it appears in
         the components model. If the port is not represented in the
         components model (e.g., a port on a passive chassis), the
         string should reflect the system assigned name of the port.
         If the source port is not within the device, then an
         identityref of EXTERNAL should be specified.";
    }
    leaf dest {
      type union {
        type string;
        type identityref {
          base PORT_CONNECTION_TYPE;
        }
      }
      description
        "The user supplied name of the destination port of the connection
         within the system. If the port is within the device, the string
         should reflect the name of the port as it appears in the
         components model. If the port is not represented in the components
         model (e.g., a port on a passive chassis), the string should
         reflect the system assigned name of the port. If the destination
         port is not within the device, then an identityref of EXTERNAL
         should be specified.";
    }
    leaf fiber-type {
      description
        "The type of fiber jumper used for the connection.";
      type identityref {
        base oc-opt-types:FIBER_JUMPER_TYPE;
      }
    }
  }

  grouping live_ncs_line-connectivity-top {
    description
      "Top level grouping for transport line connectivity data";
    container connections {
      description
        "Enclosing container for line system connections list";
      list connection {
        key "index";
        description
          "List of line system connections";
        leaf index {
          type leafref {
            path "../config/index";
          }
          description
            "Reference to index number of the connection";
        }
        container config {
          description
            "Configuration data";
          uses live_ncs_connection-config;
        }
        container state {
          description
            "Operational state data";
          uses live_ncs_connection-config;
          uses live_ncs_connection-state;
        }
      }
    }
  }

  grouping connection-state {
    description
      "Operational state data for connections";
  }

  grouping connection-config {
    description
      "Configuration data for line system connections";
    leaf index {
      type uint32;
      description
        "Index for the defined connection";
    }
    leaf source {
      type union {
        type string;
        type identityref {
          base PORT_CONNECTION_TYPE;
        }
      }
      description
        "The user supplied name of the source port of the connection
         within the system. If the port is within the device, the
         string should reflect the name of the port as it appears in
         the components model. If the port is not represented in the
         components model (e.g., a port on a passive chassis), the
         string should reflect the system assigned name of the port.
         If the source port is not within the device, then an
         identityref of EXTERNAL should be specified.";
    }
    leaf dest {
      type union {
        type string;
        type identityref {
          base PORT_CONNECTION_TYPE;
        }
      }
      description
        "The user supplied name of the destination port of the connection
         within the system. If the port is within the device, the string
         should reflect the name of the port as it appears in the
         components model. If the port is not represented in the components
         model (e.g., a port on a passive chassis), the string should
         reflect the system assigned name of the port. If the destination
         port is not within the device, then an identityref of EXTERNAL
         should be specified.";
    }
    leaf fiber-type {
      description
        "The type of fiber jumper used for the connection.";
      type identityref {
        base oc-opt-types:FIBER_JUMPER_TYPE;
      }
    }
  }

  grouping line-connectivity-top {
    description
      "Top level grouping for transport line connectivity data";
    container connections {
      description
        "Enclosing container for line system connections list";
      list connection {
        key "index";
        description
          "List of line system connections";
        leaf index {
          type leafref {
            path "../config/index";
          }
          description
            "Reference to index number of the connection";
        }
        container config {
          description
            "Configuration data";
          uses connection-config;
        }
        // NCS drop config false container state
      }
    }
  }

  augment "/ncs:devices/ncs:device/ncs:config" {
    uses line-connectivity-top {
      refine connections {
        tailf:ncs-device-type "netconf";
        tailf:display-when "not(../../ncs:module) or ../../ncs:module[ncs:name='openconfig-transport-line-connectivity']";
      }
    }
  }
  augment "/ncs:devices/ncs:device/ncs:live-status" {
    uses live_ncs_line-connectivity-top {
      refine connections {
        tailf:ncs-device-type "netconf";
        tailf:display-when "not(../../ncs:module) or ../../ncs:module[ncs:name='openconfig-transport-line-connectivity'] or (../../ncs:live-status-protocol[not(ncs:capability)]) or (../../ncs:live-status-protocol/ncs:capability/ncs:module[.='openconfig-transport-line-connectivity'])";
      }
    }
  }
  augment "/ncs:devices/ncs:template/ncs:ned-id/ncs:config" {
    uses ncs_template_line-connectivity-top;
  }

  identity EXTERNAL {
    base PORT_CONNECTION_TYPE;
    description
      "The port connection is external to the device";
  }

  identity PORT_CONNECTION_TYPE {
    description
      "The definition for different types of port connections
       when a specific port is not known";
  }
}
