module openconfig-pim {
  // Generated by yanger -t ncs
  tailf:mount-id "oc-all-nc-1.0:oc-all-nc-1.0";
  tailf:ncs-device-type "netconf";

  yang-version 1;
  namespace "http://openconfig.net/yang/pim";
  prefix oc-pim;

  import openconfig-pim-types {
    prefix oc-pim-types;
  }
  import openconfig-interfaces {
    prefix oc-if;
  }
  import openconfig-acl {
    prefix oc-acl;
  }
  import openconfig-types {
    prefix oc-types;
  }
  import openconfig-extensions {
    prefix oc-ext;
  }
  import ietf-inet-types {
    prefix inet;
  }
  import openconfig-bfd {
    prefix oc-bfd;
  }
  import tailf-common {
    prefix tailf;
  }
  import tailf-ncs {
    prefix ncs;
  }

  organization
    "OpenConfig working group";
  contact
    "OpenConfig working group
     www.openconfig.net";
  description
    "An OpenConfig model for Protocol Independent Multicast (PIM).";
  oc-ext:openconfig-version "0.4.2";

  revision 2021-06-16 {
    description
      "Remove trailing whitespace";
    reference "0.4.2";
  }
  revision 2021-04-21 {
    description
      "Reindent to two spaces and remove trailing whitespace ";
    reference "0.4.1";
  }
  revision 2021-04-21 {
    description
      "Allow to limit the maximum number of groups to join
       via PIM protocol. It can be configured at two levels,
       depending on hardware implementation:
       1. Network-instance level, the limit will apply
       to all PIM sessions/joins ending in that network-instance.
       2. Interface level, the limit would be discriminated per interface.";
    reference "0.4.0";
  }
  revision 2021-03-17 {
    description
      "Add bfd support without augmentation.";
    reference "0.3.0";
  }
  revision 2019-07-09 {
    description
      "Reindent to two spaces.
       Ensure that timeticks64 is consistently expressed in nanoseconds.";
    reference "0.2.0";
  }
  revision 2018-11-21 {
    description
      "Add OpenConfig module metadata extensions.";
    reference "0.1.1";
  }
  revision 2018-02-09 {
    description
      "Initial revision.";
    reference "0.1.0";
  }
  oc-ext:regexp-posix;
  oc-ext:catalog-organization "openconfig";
  oc-ext:origin "openconfig";

  grouping ncs_template_admin-config {
    description
      "Re-usable grouping to enable or disable a particular feature.";
    leaf enabled {
      type string;
      // NCS drop default statement
      description
        "When set to true, the functionality within which this
         leaf is defined is enabled, when set to false it is
         explicitly disabled.";
    }
  }

  grouping ncs_template_pim-counters-state {
    description
      "Counters related to PIM messages.";
    leaf hello-messages {
      type string;
      description
        "Number of hello messages received.";
      reference "RFC7761 4.9.2 page 108";
    }
    leaf join-prune-messages {
      type string;
      description
        "Number of join/prune messages received.";
      reference "RFC7761 4.5 page 44";
    }
    leaf bootstrap-messages {
      type string;
      description
        "Number of bootstrap router messages received.";
      reference "RFC7761 3.7 page 12";
    }
  }

  grouping ncs_template_pim-interface-config {
    description
      "Configuration data for PIM on each interface.";
    uses ncs_template_admin-config;
    leaf interface-id {
      type oc-if:ncs_template_interface-id;
      description
        "Reference to an interface on which PIM is enabled.";
    }
    leaf mode {
      type string;
      description
        "PIM mode to use when delivering multicast traffic via this
         interface.";
    }
    leaf bsr-border {
      type string;
      // NCS drop default statement
      description
        "When set to true the device will not send bootstrap router
         messages over this interface. By default these are transmitted
         over all PIM sparse mode (PIM-SM) enabled interfaces.";
    }
    leaf border-router {
      type string;
      // NCS drop default statement
      description
        "When set to true the interface is set as MBR (multicast border
         router) and allows multicast traffic from sources that are
         outside of the PIM domain.";
    }
    leaf dr-priority {
      type oc-pim-types:ncs_template_dr-priority-type;
      description
        "The designated router priority of this interface. Larger always
         preferred.";
    }
    leaf join-prune-interval {
      type oc-pim-types:ncs_template_pim-interval-type;
      description
        "Interval at which the router sends the PIM join/prune messages
         toward the upstream RPF neighbor.";
    }
    leaf hello-interval {
      type oc-pim-types:ncs_template_pim-interval-type;
      description
        "Interval at which the router sends the PIM hello messages.";
    }
    leaf dead-timer {
      type string;
      description
        "Number of missed hello messages after which a neighbor is
         expired.";
    }
    leaf maximum-groups {
      type string;
      description
        "Limit the number of (S, G) and (*, G) PIM
         entries accepted on the interface.
         This feature depends on hardware implementation.";
    }
  }

  grouping ncs_template_pim-neighbor-state {
    description
      "PIM neighbor state.";
    leaf neighbor-address {
      type string;
      description
        "IPv4 address of neighbor router.";
    }
    leaf dr-address {
      type string;
      description
        "IPv4 address of designated router.";
    }
    leaf neighbor-established {
      type oc-types:ncs_template_timeticks64;
      description
        "This timestamp indicates the time that the
         PIM neighbor adjacency established. It is expressed
         relative to the Unix Epoch (Jan 1, 1970 00:00:00 UTC).

         The PIM session uptime can be computed by clients
         as the difference between this value and the
         current time in UTC.";
    }
    leaf neighbor-expires {
      type oc-types:ncs_template_timeticks64;
      description
        "This timestamp indicates the time that the
         PIM neighbor adjacency will expire should hello
         messages fail to arrive from the neighbor. The value
         is expressed relative to the Unix Epoch (Jan 1, 1970
         00:00:00 UTC).";
    }
    leaf mode {
      type string;
      description
        "PIM mode in use when delivering multicast traffic
         via this neighbor.";
    }
  }

  grouping ncs_template_pim-neighbors-top {
    description
      "Details about PIM neighbors.";
    // NCS drop config false container neighbors
  }

  grouping ncs_template_pim-interfaces-top {
    description
      "Configuration and state data for PIM on each interface.";
    container interfaces {
      description
        "Configuration and state data for PIM on each interface.";
      list interface {
        // NCS patched for predictable order
        ordered-by user;
        key "interface-id";
        description
          "This container defines interface PIM configuration and
           state information.";
        leaf interface-id {
          type string;
          description
            "Reference to an interface on which PIM is enabled.";
        }
        container config {
          description
            "PIM interface configuration.";
          uses ncs_template_pim-interface-config;
        }
        // NCS drop config false container state
        uses ncs_template_pim-neighbors-top;
        uses oc-if:ncs_template_interface-ref;
        uses oc-bfd:ncs_template_bfd-enable;
      }
    }
  }

  grouping ncs_template_pim-global-config {
    description
      "Configuration data for PIM.";
    leaf maximum-groups {
      type string;
      description
        "Limit the number of accepted (S, G) and (*, G)
         PIM join states on the network-instance.";
    }
  }

  grouping ncs_template_pim-global-state {
    description
      "State and session data for PIM on each interface.";
    leaf neighbor-count {
      type string;
      description
        "Number of adjacent PIM neighbors.";
    }
    container counters {
      description
        "Global PIM counters.";
      uses ncs_template_pim-counters-state;
    }
  }

  grouping ncs_template_pim-sources-joined-top {
    description
      "List of multicast sources joined.";
    // NCS drop config false container 'sources-joined'
  }

  grouping ncs_template_pim-global-ssm-config {
    description
      "Source specific multicast (SSM) configuration.";
    leaf ssm-ranges {
      type string;
      description
        "List of accepted source specific multicast (SSM) address
         ranges.";
    }
  }

  grouping ncs_template_pim-global-rp-addresses-config {
    description
      "Defines rendezvous points for sparse mode multicast.";
    leaf address {
      type string;
      description
        "IPv4 address of rendezvous point.";
    }
    leaf multicast-groups {
      type string;
      description
        "List of multicast groups (multicast IP address ranges) for which
         this entry will be used as a rendezvous point. When not
         present the default is equivalent to all valid IP multicast
         addresses.";
    }
  }

  grouping ncs_template_pim-global-top {
    description
      "Top level grouping for global PIM configuration.";
    container config {
      description
        "Configuration for global PIM parameters";
      uses ncs_template_pim-global-config;
    }
    // NCS drop config false container state
    container ssm {
      description
        "Source specific multicast (SSM).";
      container config {
        description
          "Configuration for source specific multicast (SSM).";
        uses ncs_template_pim-global-ssm-config;
      }
      // NCS drop config false container state
    }
    container rendezvous-points {
      description
        "Defines rendezvous points for sparse mode multicast.";
      list rendezvous-point {
        // NCS patched for predictable order
        ordered-by user;
        key "address";
        description
          "Defines a rendezvous point (RP) for sparse mode multicast.";
        leaf address {
          type string;
          description
            "IPv4 address of rendezvous point.";
        }
        container config {
          description
            "Rendezvous point configuration.";
          uses ncs_template_pim-global-rp-addresses-config;
        }
        // NCS drop config false container state
      }
    }
    uses ncs_template_pim-sources-joined-top;
  }

  grouping ncs_template_pim-top {
    description
      "Top-level grouping for PIM.";
    container pim {
      description
        "Top-level PIM configuration and operational state.";
      container global {
        description
          "This container defines global PIM configuration and state
           information.";
        uses ncs_template_pim-global-top;
      }
      uses ncs_template_pim-interfaces-top;
    }
  }

  grouping ncs_rpc_notif_admin-config {
    description
      "Re-usable grouping to enable or disable a particular feature.";
    leaf enabled {
      type boolean;
      default "false";
      description
        "When set to true, the functionality within which this
         leaf is defined is enabled, when set to false it is
         explicitly disabled.";
    }
  }

  grouping ncs_rpc_notif_pim-counters-state {
    description
      "Counters related to PIM messages.";
    leaf hello-messages {
      type uint32;
      description
        "Number of hello messages received.";
      reference "RFC7761 4.9.2 page 108";
    }
    leaf join-prune-messages {
      type uint32;
      description
        "Number of join/prune messages received.";
      reference "RFC7761 4.5 page 44";
    }
    leaf bootstrap-messages {
      type uint32;
      description
        "Number of bootstrap router messages received.";
      reference "RFC7761 3.7 page 12";
    }
  }

  grouping ncs_rpc_notif_pim-interface-config {
    description
      "Configuration data for PIM on each interface.";
    uses ncs_rpc_notif_admin-config;
    leaf interface-id {
      type oc-if:ncs_rpc_notif_interface-id;
      description
        "Reference to an interface on which PIM is enabled.";
    }
    leaf mode {
      type identityref {
        base oc-pim-types:PIM_MODE;
      }
      description
        "PIM mode to use when delivering multicast traffic via this
         interface.";
    }
    leaf bsr-border {
      type boolean;
      default "false";
      description
        "When set to true the device will not send bootstrap router
         messages over this interface. By default these are transmitted
         over all PIM sparse mode (PIM-SM) enabled interfaces.";
    }
    leaf border-router {
      type boolean;
      default "false";
      description
        "When set to true the interface is set as MBR (multicast border
         router) and allows multicast traffic from sources that are
         outside of the PIM domain.";
    }
    leaf dr-priority {
      type oc-pim-types:ncs_rpc_notif_dr-priority-type;
      description
        "The designated router priority of this interface. Larger always
         preferred.";
    }
    leaf join-prune-interval {
      type oc-pim-types:ncs_rpc_notif_pim-interval-type;
      description
        "Interval at which the router sends the PIM join/prune messages
         toward the upstream RPF neighbor.";
    }
    leaf hello-interval {
      type oc-pim-types:ncs_rpc_notif_pim-interval-type;
      description
        "Interval at which the router sends the PIM hello messages.";
    }
    leaf dead-timer {
      type uint16 {
        range "1..65535";
      }
      description
        "Number of missed hello messages after which a neighbor is
         expired.";
    }
    leaf maximum-groups {
      type uint32;
      description
        "Limit the number of (S, G) and (*, G) PIM
         entries accepted on the interface.
         This feature depends on hardware implementation.";
    }
  }

  grouping ncs_rpc_notif_pim-neighbor-state {
    description
      "PIM neighbor state.";
    leaf neighbor-address {
      type inet:ipv4-address;
      description
        "IPv4 address of neighbor router.";
    }
    leaf dr-address {
      type inet:ipv4-address;
      description
        "IPv4 address of designated router.";
    }
    leaf neighbor-established {
      type oc-types:ncs_rpc_notif_timeticks64;
      description
        "This timestamp indicates the time that the
         PIM neighbor adjacency established. It is expressed
         relative to the Unix Epoch (Jan 1, 1970 00:00:00 UTC).

         The PIM session uptime can be computed by clients
         as the difference between this value and the
         current time in UTC.";
    }
    leaf neighbor-expires {
      type oc-types:ncs_rpc_notif_timeticks64;
      description
        "This timestamp indicates the time that the
         PIM neighbor adjacency will expire should hello
         messages fail to arrive from the neighbor. The value
         is expressed relative to the Unix Epoch (Jan 1, 1970
         00:00:00 UTC).";
    }
    leaf mode {
      type identityref {
        base oc-pim-types:PIM_MODE;
      }
      description
        "PIM mode in use when delivering multicast traffic
         via this neighbor.";
    }
  }

  grouping ncs_rpc_notif_pim-neighbors-top {
    description
      "Details about PIM neighbors.";
    container neighbors {
      config false;
      description
        "Details about PIM neighbors.";
      list neighbor {
        key "neighbor-address";
        description
          "Details about a specific PIM neighbor.";
        leaf neighbor-address {
          type leafref {
            path "../state/neighbor-address";
          }
          description
            "IPv4 address of neighbor router.";
        }
        container state {
          config false;
          description
            "Details about a specific PIM neighbor.";
          uses ncs_rpc_notif_pim-neighbor-state;
        }
      }
    }
  }

  grouping ncs_rpc_notif_pim-interfaces-top {
    description
      "Configuration and state data for PIM on each interface.";
    container interfaces {
      description
        "Configuration and state data for PIM on each interface.";
      list interface {
        key "interface-id";
        description
          "This container defines interface PIM configuration and
           state information.";
        leaf interface-id {
          type leafref {
            path "../config/interface-id";
          }
          description
            "Reference to an interface on which PIM is enabled.";
        }
        container config {
          description
            "PIM interface configuration.";
          uses ncs_rpc_notif_pim-interface-config;
        }
        container state {
          config false;
          description
            "State information for PIM interfaces.";
          uses ncs_rpc_notif_pim-interface-config;
          container counters {
            description
              "PIM counters for each interface.";
            uses ncs_rpc_notif_pim-counters-state;
          }
        }
        uses ncs_rpc_notif_pim-neighbors-top;
        uses oc-if:ncs_rpc_notif_interface-ref;
        uses oc-bfd:ncs_rpc_notif_bfd-enable;
      }
    }
  }

  grouping ncs_rpc_notif_pim-global-config {
    description
      "Configuration data for PIM.";
    leaf maximum-groups {
      type uint32;
      description
        "Limit the number of accepted (S, G) and (*, G)
         PIM join states on the network-instance.";
    }
  }

  grouping ncs_rpc_notif_pim-global-state {
    description
      "State and session data for PIM on each interface.";
    leaf neighbor-count {
      type uint8;
      description
        "Number of adjacent PIM neighbors.";
    }
    container counters {
      description
        "Global PIM counters.";
      uses ncs_rpc_notif_pim-counters-state;
    }
  }

  grouping ncs_rpc_notif_pim-sources-joined-top {
    description
      "List of multicast sources joined.";
    container sources-joined {
      config false;
      description
        "List of multicast sources joined.";
      list source {
        key "address";
        description
          "A multicast source that has been joined.";
        leaf address {
          type leafref {
            path "../state/address";
          }
          description
            "Source address of multicast.";
        }
        container state {
          config false;
          description
            "State for a multicast source that has been joined.";
          leaf address {
            type inet:ipv4-address;
            description
              "Source address of multicast.";
          }
          leaf group {
            type inet:ipv4-address;
            description
              "Multicast address.";
          }
          leaf upstream-interface-id {
            type oc-if:ncs_rpc_notif_interface-id;
            description
              "The upstream interface for this multicast source.";
          }
        }
      }
    }
  }

  grouping ncs_rpc_notif_pim-global-ssm-config {
    description
      "Source specific multicast (SSM) configuration.";
    leaf ssm-ranges {
      type string;
      description
        "List of accepted source specific multicast (SSM) address
         ranges.";
    }
  }

  grouping ncs_rpc_notif_pim-global-rp-addresses-config {
    description
      "Defines rendezvous points for sparse mode multicast.";
    leaf address {
      type inet:ipv4-address;
      description
        "IPv4 address of rendezvous point.";
    }
    leaf multicast-groups {
      type string;
      description
        "List of multicast groups (multicast IP address ranges) for which
         this entry will be used as a rendezvous point. When not
         present the default is equivalent to all valid IP multicast
         addresses.";
    }
  }

  grouping ncs_rpc_notif_pim-global-top {
    description
      "Top level grouping for global PIM configuration.";
    container config {
      description
        "Configuration for global PIM parameters";
      uses ncs_rpc_notif_pim-global-config;
    }
    container state {
      config false;
      description
        "Global PIM state.";
      uses ncs_rpc_notif_pim-global-config;
      uses ncs_rpc_notif_pim-global-state;
    }
    container ssm {
      description
        "Source specific multicast (SSM).";
      container config {
        description
          "Configuration for source specific multicast (SSM).";
        uses ncs_rpc_notif_pim-global-ssm-config;
      }
      container state {
        config false;
        description
          "State for source specific multicast (SSM).";
        uses ncs_rpc_notif_pim-global-ssm-config;
      }
    }
    container rendezvous-points {
      description
        "Defines rendezvous points for sparse mode multicast.";
      list rendezvous-point {
        key "address";
        description
          "Defines a rendezvous point (RP) for sparse mode multicast.";
        leaf address {
          type leafref {
            path "../config/address";
          }
          description
            "IPv4 address of rendezvous point.";
        }
        container config {
          description
            "Rendezvous point configuration.";
          uses ncs_rpc_notif_pim-global-rp-addresses-config;
        }
        container state {
          config false;
          description
            "Rendezvous point state.";
          uses ncs_rpc_notif_pim-global-rp-addresses-config;
        }
      }
    }
    uses ncs_rpc_notif_pim-sources-joined-top;
  }

  grouping ncs_rpc_notif_pim-top {
    description
      "Top-level grouping for PIM.";
    container pim {
      description
        "Top-level PIM configuration and operational state.";
      container global {
        description
          "This container defines global PIM configuration and state
           information.";
        uses ncs_rpc_notif_pim-global-top;
      }
      uses ncs_rpc_notif_pim-interfaces-top;
    }
  }

  grouping live_ncs_admin-config {
    description
      "Re-usable grouping to enable or disable a particular feature.";
    leaf enabled {
      type boolean;
      // NCS drop default statement
      description
        "When set to true, the functionality within which this
         leaf is defined is enabled, when set to false it is
         explicitly disabled.";
    }
  }

  grouping live_ncs_pim-counters-state {
    description
      "Counters related to PIM messages.";
    leaf hello-messages {
      type uint32;
      description
        "Number of hello messages received.";
      reference "RFC7761 4.9.2 page 108";
    }
    leaf join-prune-messages {
      type uint32;
      description
        "Number of join/prune messages received.";
      reference "RFC7761 4.5 page 44";
    }
    leaf bootstrap-messages {
      type uint32;
      description
        "Number of bootstrap router messages received.";
      reference "RFC7761 3.7 page 12";
    }
  }

  grouping live_ncs_pim-interface-config {
    description
      "Configuration data for PIM on each interface.";
    uses live_ncs_admin-config;
    leaf interface-id {
      type oc-if:live_ncs_interface-id;
      description
        "Reference to an interface on which PIM is enabled.";
    }
    leaf mode {
      type identityref {
        base oc-pim-types:PIM_MODE;
      }
      description
        "PIM mode to use when delivering multicast traffic via this
         interface.";
    }
    leaf bsr-border {
      type boolean;
      // NCS drop default statement
      description
        "When set to true the device will not send bootstrap router
         messages over this interface. By default these are transmitted
         over all PIM sparse mode (PIM-SM) enabled interfaces.";
    }
    leaf border-router {
      type boolean;
      // NCS drop default statement
      description
        "When set to true the interface is set as MBR (multicast border
         router) and allows multicast traffic from sources that are
         outside of the PIM domain.";
    }
    leaf dr-priority {
      type oc-pim-types:live_ncs_dr-priority-type;
      description
        "The designated router priority of this interface. Larger always
         preferred.";
    }
    leaf join-prune-interval {
      type oc-pim-types:live_ncs_pim-interval-type;
      description
        "Interval at which the router sends the PIM join/prune messages
         toward the upstream RPF neighbor.";
    }
    leaf hello-interval {
      type oc-pim-types:live_ncs_pim-interval-type;
      description
        "Interval at which the router sends the PIM hello messages.";
    }
    leaf dead-timer {
      type uint16 {
        range "1..65535";
      }
      description
        "Number of missed hello messages after which a neighbor is
         expired.";
    }
    leaf maximum-groups {
      type uint32;
      description
        "Limit the number of (S, G) and (*, G) PIM
         entries accepted on the interface.
         This feature depends on hardware implementation.";
    }
  }

  grouping live_ncs_pim-neighbor-state {
    description
      "PIM neighbor state.";
    leaf neighbor-address {
      type inet:ipv4-address;
      description
        "IPv4 address of neighbor router.";
    }
    leaf dr-address {
      type inet:ipv4-address;
      description
        "IPv4 address of designated router.";
    }
    leaf neighbor-established {
      type oc-types:live_ncs_timeticks64;
      description
        "This timestamp indicates the time that the
         PIM neighbor adjacency established. It is expressed
         relative to the Unix Epoch (Jan 1, 1970 00:00:00 UTC).

         The PIM session uptime can be computed by clients
         as the difference between this value and the
         current time in UTC.";
    }
    leaf neighbor-expires {
      type oc-types:live_ncs_timeticks64;
      description
        "This timestamp indicates the time that the
         PIM neighbor adjacency will expire should hello
         messages fail to arrive from the neighbor. The value
         is expressed relative to the Unix Epoch (Jan 1, 1970
         00:00:00 UTC).";
    }
    leaf mode {
      type identityref {
        base oc-pim-types:PIM_MODE;
      }
      description
        "PIM mode in use when delivering multicast traffic
         via this neighbor.";
    }
  }

  grouping live_ncs_pim-neighbors-top {
    description
      "Details about PIM neighbors.";
    container neighbors {
      description
        "Details about PIM neighbors.";
      list neighbor {
        key "neighbor-address";
        description
          "Details about a specific PIM neighbor.";
        leaf neighbor-address {
          type leafref {
            path "../state/neighbor-address";
          }
          description
            "IPv4 address of neighbor router.";
        }
        container state {
          description
            "Details about a specific PIM neighbor.";
          uses live_ncs_pim-neighbor-state;
        }
      }
    }
  }

  grouping live_ncs_pim-interfaces-top {
    description
      "Configuration and state data for PIM on each interface.";
    container interfaces {
      description
        "Configuration and state data for PIM on each interface.";
      list interface {
        key "interface-id";
        description
          "This container defines interface PIM configuration and
           state information.";
        leaf interface-id {
          type leafref {
            path "../config/interface-id";
          }
          description
            "Reference to an interface on which PIM is enabled.";
        }
        container config {
          description
            "PIM interface configuration.";
          uses live_ncs_pim-interface-config;
        }
        container state {
          description
            "State information for PIM interfaces.";
          uses live_ncs_pim-interface-config;
          container counters {
            description
              "PIM counters for each interface.";
            uses live_ncs_pim-counters-state;
          }
        }
        uses live_ncs_pim-neighbors-top;
        uses oc-if:live_ncs_interface-ref;
        uses oc-bfd:live_ncs_bfd-enable;
      }
    }
  }

  grouping live_ncs_pim-global-config {
    description
      "Configuration data for PIM.";
    leaf maximum-groups {
      type uint32;
      description
        "Limit the number of accepted (S, G) and (*, G)
         PIM join states on the network-instance.";
    }
  }

  grouping live_ncs_pim-global-state {
    description
      "State and session data for PIM on each interface.";
    leaf neighbor-count {
      type uint8;
      description
        "Number of adjacent PIM neighbors.";
    }
    container counters {
      description
        "Global PIM counters.";
      uses live_ncs_pim-counters-state;
    }
  }

  grouping live_ncs_pim-sources-joined-top {
    description
      "List of multicast sources joined.";
    container sources-joined {
      description
        "List of multicast sources joined.";
      list source {
        key "address";
        description
          "A multicast source that has been joined.";
        leaf address {
          type leafref {
            path "../state/address";
          }
          description
            "Source address of multicast.";
        }
        container state {
          description
            "State for a multicast source that has been joined.";
          leaf address {
            type inet:ipv4-address;
            description
              "Source address of multicast.";
          }
          leaf group {
            type inet:ipv4-address;
            description
              "Multicast address.";
          }
          leaf upstream-interface-id {
            type oc-if:live_ncs_interface-id;
            description
              "The upstream interface for this multicast source.";
          }
        }
      }
    }
  }

  grouping live_ncs_pim-global-ssm-config {
    description
      "Source specific multicast (SSM) configuration.";
    leaf ssm-ranges {
      type leafref {
        path "/ncs:devices/ncs:device/ncs:live-status/oc-acl:acl/oc-acl:acl-sets/oc-acl:acl-set/oc-acl:config/oc-acl:name" {
          tailf:xpath-root 3;
        }
      }
      description
        "List of accepted source specific multicast (SSM) address
         ranges.";
    }
  }

  grouping live_ncs_pim-global-rp-addresses-config {
    description
      "Defines rendezvous points for sparse mode multicast.";
    leaf address {
      type inet:ipv4-address;
      description
        "IPv4 address of rendezvous point.";
    }
    leaf multicast-groups {
      type string;
      description
        "List of multicast groups (multicast IP address ranges) for which
         this entry will be used as a rendezvous point. When not
         present the default is equivalent to all valid IP multicast
         addresses.";
    }
  }

  grouping live_ncs_pim-global-top {
    description
      "Top level grouping for global PIM configuration.";
    container config {
      description
        "Configuration for global PIM parameters";
      uses live_ncs_pim-global-config;
    }
    container state {
      description
        "Global PIM state.";
      uses live_ncs_pim-global-config;
      uses live_ncs_pim-global-state;
    }
    container ssm {
      description
        "Source specific multicast (SSM).";
      container config {
        description
          "Configuration for source specific multicast (SSM).";
        uses live_ncs_pim-global-ssm-config;
      }
      container state {
        description
          "State for source specific multicast (SSM).";
        uses live_ncs_pim-global-ssm-config;
      }
    }
    container rendezvous-points {
      description
        "Defines rendezvous points for sparse mode multicast.";
      list rendezvous-point {
        key "address";
        description
          "Defines a rendezvous point (RP) for sparse mode multicast.";
        leaf address {
          type leafref {
            path "../config/address";
          }
          description
            "IPv4 address of rendezvous point.";
        }
        container config {
          description
            "Rendezvous point configuration.";
          uses live_ncs_pim-global-rp-addresses-config;
        }
        container state {
          description
            "Rendezvous point state.";
          uses live_ncs_pim-global-rp-addresses-config;
        }
      }
    }
    uses live_ncs_pim-sources-joined-top;
  }

  grouping live_ncs_pim-top {
    description
      "Top-level grouping for PIM.";
    container pim {
      description
        "Top-level PIM configuration and operational state.";
      container global {
        description
          "This container defines global PIM configuration and state
           information.";
        uses live_ncs_pim-global-top;
      }
      uses live_ncs_pim-interfaces-top;
    }
  }

  grouping admin-config {
    description
      "Re-usable grouping to enable or disable a particular feature.";
    leaf enabled {
      type boolean;
      default "false";
      description
        "When set to true, the functionality within which this
         leaf is defined is enabled, when set to false it is
         explicitly disabled.";
    }
  }

  grouping pim-counters-state {
    description
      "Counters related to PIM messages.";
    leaf hello-messages {
      type uint32;
      description
        "Number of hello messages received.";
      reference "RFC7761 4.9.2 page 108";
    }
    leaf join-prune-messages {
      type uint32;
      description
        "Number of join/prune messages received.";
      reference "RFC7761 4.5 page 44";
    }
    leaf bootstrap-messages {
      type uint32;
      description
        "Number of bootstrap router messages received.";
      reference "RFC7761 3.7 page 12";
    }
  }

  grouping pim-interface-config {
    description
      "Configuration data for PIM on each interface.";
    uses admin-config;
    leaf interface-id {
      type oc-if:interface-id;
      description
        "Reference to an interface on which PIM is enabled.";
    }
    leaf mode {
      type identityref {
        base oc-pim-types:PIM_MODE;
      }
      description
        "PIM mode to use when delivering multicast traffic via this
         interface.";
    }
    leaf bsr-border {
      type boolean;
      default "false";
      description
        "When set to true the device will not send bootstrap router
         messages over this interface. By default these are transmitted
         over all PIM sparse mode (PIM-SM) enabled interfaces.";
    }
    leaf border-router {
      type boolean;
      default "false";
      description
        "When set to true the interface is set as MBR (multicast border
         router) and allows multicast traffic from sources that are
         outside of the PIM domain.";
    }
    leaf dr-priority {
      type oc-pim-types:dr-priority-type;
      description
        "The designated router priority of this interface. Larger always
         preferred.";
    }
    leaf join-prune-interval {
      type oc-pim-types:pim-interval-type;
      description
        "Interval at which the router sends the PIM join/prune messages
         toward the upstream RPF neighbor.";
    }
    leaf hello-interval {
      type oc-pim-types:pim-interval-type;
      description
        "Interval at which the router sends the PIM hello messages.";
    }
    leaf dead-timer {
      type uint16 {
        range "1..65535";
      }
      description
        "Number of missed hello messages after which a neighbor is
         expired.";
    }
    leaf maximum-groups {
      type uint32;
      description
        "Limit the number of (S, G) and (*, G) PIM
         entries accepted on the interface.
         This feature depends on hardware implementation.";
    }
  }

  grouping pim-neighbor-state {
    description
      "PIM neighbor state.";
    leaf neighbor-address {
      type inet:ipv4-address;
      description
        "IPv4 address of neighbor router.";
    }
    leaf dr-address {
      type inet:ipv4-address;
      description
        "IPv4 address of designated router.";
    }
    leaf neighbor-established {
      type oc-types:timeticks64;
      description
        "This timestamp indicates the time that the
         PIM neighbor adjacency established. It is expressed
         relative to the Unix Epoch (Jan 1, 1970 00:00:00 UTC).

         The PIM session uptime can be computed by clients
         as the difference between this value and the
         current time in UTC.";
    }
    leaf neighbor-expires {
      type oc-types:timeticks64;
      description
        "This timestamp indicates the time that the
         PIM neighbor adjacency will expire should hello
         messages fail to arrive from the neighbor. The value
         is expressed relative to the Unix Epoch (Jan 1, 1970
         00:00:00 UTC).";
    }
    leaf mode {
      type identityref {
        base oc-pim-types:PIM_MODE;
      }
      description
        "PIM mode in use when delivering multicast traffic
         via this neighbor.";
    }
  }

  grouping pim-neighbors-top {
    description
      "Details about PIM neighbors.";
    // NCS drop config false container neighbors
  }

  grouping pim-interfaces-top {
    description
      "Configuration and state data for PIM on each interface.";
    container interfaces {
      description
        "Configuration and state data for PIM on each interface.";
      list interface {
        key "interface-id";
        description
          "This container defines interface PIM configuration and
           state information.";
        leaf interface-id {
          type leafref {
            path "../config/interface-id";
          }
          description
            "Reference to an interface on which PIM is enabled.";
        }
        container config {
          description
            "PIM interface configuration.";
          uses pim-interface-config;
        }
        // NCS drop config false container state
        uses pim-neighbors-top;
        uses oc-if:interface-ref;
        uses oc-bfd:bfd-enable;
      }
    }
  }

  grouping pim-global-config {
    description
      "Configuration data for PIM.";
    leaf maximum-groups {
      type uint32;
      description
        "Limit the number of accepted (S, G) and (*, G)
         PIM join states on the network-instance.";
    }
  }

  grouping pim-global-state {
    description
      "State and session data for PIM on each interface.";
    leaf neighbor-count {
      type uint8;
      description
        "Number of adjacent PIM neighbors.";
    }
    container counters {
      description
        "Global PIM counters.";
      uses pim-counters-state;
    }
  }

  grouping pim-sources-joined-top {
    description
      "List of multicast sources joined.";
    // NCS drop config false container 'sources-joined'
  }

  grouping pim-global-ssm-config {
    description
      "Source specific multicast (SSM) configuration.";
    leaf ssm-ranges {
      type leafref {
        path "/ncs:devices/ncs:device/ncs:config/oc-acl:acl/oc-acl:acl-sets/oc-acl:acl-set/oc-acl:config/oc-acl:name" {
          tailf:xpath-root 3;
        }
      }
      description
        "List of accepted source specific multicast (SSM) address
         ranges.";
    }
  }

  grouping pim-global-rp-addresses-config {
    description
      "Defines rendezvous points for sparse mode multicast.";
    leaf address {
      type inet:ipv4-address;
      description
        "IPv4 address of rendezvous point.";
    }
    leaf multicast-groups {
      type string;
      description
        "List of multicast groups (multicast IP address ranges) for which
         this entry will be used as a rendezvous point. When not
         present the default is equivalent to all valid IP multicast
         addresses.";
    }
  }

  grouping pim-global-top {
    description
      "Top level grouping for global PIM configuration.";
    container config {
      description
        "Configuration for global PIM parameters";
      uses pim-global-config;
    }
    // NCS drop config false container state
    container ssm {
      description
        "Source specific multicast (SSM).";
      container config {
        description
          "Configuration for source specific multicast (SSM).";
        uses pim-global-ssm-config;
      }
      // NCS drop config false container state
    }
    container rendezvous-points {
      description
        "Defines rendezvous points for sparse mode multicast.";
      list rendezvous-point {
        key "address";
        description
          "Defines a rendezvous point (RP) for sparse mode multicast.";
        leaf address {
          type leafref {
            path "../config/address";
          }
          description
            "IPv4 address of rendezvous point.";
        }
        container config {
          description
            "Rendezvous point configuration.";
          uses pim-global-rp-addresses-config;
        }
        // NCS drop config false container state
      }
    }
    uses pim-sources-joined-top;
  }

  grouping pim-top {
    description
      "Top-level grouping for PIM.";
    container pim {
      description
        "Top-level PIM configuration and operational state.";
      container global {
        description
          "This container defines global PIM configuration and state
           information.";
        uses pim-global-top;
      }
      uses pim-interfaces-top;
    }
  }
}
