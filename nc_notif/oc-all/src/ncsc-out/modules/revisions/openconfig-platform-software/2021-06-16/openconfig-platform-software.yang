module openconfig-platform-software {
  // Generated by yanger -t ncs
  tailf:mount-id "oc-all-nc-1.0:oc-all-nc-1.0";
  tailf:ncs-device-type "netconf";

  yang-version 1;
  namespace "http://openconfig.net/yang/platform/software-module";
  prefix oc-sw-module;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
      www.openconfig.net";
  description
    "This module defines data related to software components in
      the openconfig-platform model";
  oc-ext:openconfig-version "0.1.1";

  revision 2021-06-16 {
    description
      "Remove trailing whitespace";
    reference "0.1.1";
  }
  revision 2021-01-18 {
    description
      "Initial revision.";
    reference "0.1.0";
  }
  oc-ext:catalog-organization "openconfig";
  oc-ext:origin "openconfig";

  grouping ncs_template_sw-module-state {
    description
      "Operational state data for software module components";
    leaf module-type {
      type string;
      description
        "Type of the software module";
    }
  }

  grouping ncs_rpc_notif_sw-module-state {
    description
      "Operational state data for software module components";
    leaf module-type {
      type identityref {
        base SOFTWARE_MODULE_TYPE;
      }
      description
        "Type of the software module";
    }
  }

  grouping live_ncs_sw-module-state {
    description
      "Operational state data for software module components";
    leaf module-type {
      type identityref {
        base SOFTWARE_MODULE_TYPE;
      }
      description
        "Type of the software module";
    }
  }

  grouping sw-module-state {
    description
      "Operational state data for software module components";
    leaf module-type {
      type identityref {
        base SOFTWARE_MODULE_TYPE;
      }
      description
        "Type of the software module";
    }
  }

  augment "/ncs:devices/ncs:device/ncs:live-status/oc-platform:components/oc-platform:component/oc-platform:software-module/oc-platform:state" {
    description
      "Adding software module operational data to physical inventory.
       This subtree is only valid when the type of the component is
       SOFTWARE_MODULE.";
    uses live_ncs_sw-module-state {
      refine module-type {
        tailf:ncs-device-type "netconf";
        tailf:display-when "not(../../../../../../ncs:module) or ../../../../../../ncs:module[ncs:name='openconfig-platform-software'] or (../../../../../../ncs:live-status-protocol[not(ncs:capability)]) or (../../../../../../ncs:live-status-protocol/ncs:capability/ncs:module[.='openconfig-platform-software'])";
      }
    }
  }

  identity USERSPACE_PACKAGE {
    base SOFTWARE_MODULE_TYPE;
    description
      "An individual software package that runs in user space. The
       package may be part of a package bundle.";
  }

  identity USERSPACE_PACKAGE_BUNDLE {
    base SOFTWARE_MODULE_TYPE;
    description
      "A collection of userspace software modules that are grouped, and
       possibly versioned, together.  A package bundle may have
       subcomponents that represent individual elements in the bundle
       and their properties.";
  }

  identity SOFTWARE_MODULE_TYPE {
    description
      "Base identity for defining various types of software
       modules.";
  }
}
