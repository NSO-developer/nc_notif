module openconfig-ospf-policy {
  // Generated by yanger -t ncs
  tailf:mount-id "oc-all-nc-1.0:oc-all-nc-1.0";
  tailf:ncs-device-type "netconf";

  yang-version 1;
  namespace "http://openconfig.net/yang/ospf-policy";
  prefix oc-ospf-pol;

  import openconfig-routing-policy {
    prefix oc-rpol;
  }
  import openconfig-extensions {
    prefix oc-ext;
  }
  import openconfig-ospf-types {
    prefix oc-ospf-types;
  }
  import tailf-common {
    prefix tailf;
  }
  import tailf-ncs {
    prefix ncs;
  }

  organization
    "OpenConfig working group";
  contact
    "OpenConfig working group
     www.openconfig.net";
  description
    "This module defines extensions to the OpenConfig policy
     model to add extensions for OSPF. This module is intended
     to be generic for both OSPFv2 and OSPFv3.";
  oc-ext:openconfig-version "0.1.3";

  revision 2018-11-21 {
    description
      "Add OpenConfig module metadata extensions.";
    reference "0.1.3";
  }
  revision 2018-06-05 {
    description
      "Bug fixes in when statements in lsdb";
    reference "0.1.2";
  }
  revision 2017-08-24 {
    description
      "Minor formatting fixes.";
    reference "0.1.1";
  }
  revision 2016-08-22 {
    description
      "Initial revision";
    reference "0.0.1";
  }
  oc-ext:regexp-posix;
  oc-ext:catalog-organization "openconfig";
  oc-ext:origin "openconfig";

  grouping ncs_template_ospf-match-config {
    description
      "Configuration parameters for OSPF match conditions";
    leaf area-eq {
      type oc-ospf-types:ncs_template_ospf-area-identifier;
      description
        "Match prefixes which are within a particular OSPF area";
    }
  }

  grouping ncs_template_ospf-match-conditions {
    description
      "Match conditions that are added by OSPF";
    container ospf-conditions {
      description
        "Match conditions specific to OSPF";
      container config {
        description
          "Configuration parameters relating to OSPF match conditions";
        uses ncs_template_ospf-match-config;
      }
      // NCS drop config false container state
    }
  }

  grouping ncs_template_ospf-actions-config {
    description
      "Configuration parameters for OSPF policy actions";
    leaf set-area {
      type oc-ospf-types:ncs_template_ospf-area-identifier;
      description
        "Set the area for the matched route. This action is typically
         used when importing prefixes into OSPF, such that a route can
         be imported into a specific area within the instance.";
    }
  }

  grouping ncs_template_ospf-actions-set-metric-config {
    description
      "Configuration parameters relating to setting the OSPF metric";
    leaf metric-type {
      type string;
      // NCS drop default statement
      description
        "Specify the type of metric which is to be set by the policy";
    }
    leaf metric {
      type oc-ospf-types:ncs_template_ospf-metric;
      description
        "Set the metric of the routes matching the policy to the value
         specified by this leaf.";
    }
  }

  grouping ncs_template_ospf-actions {
    description
      "Actions that are added by OSPF to the action framework";
    container ospf-actions {
      description
        "Actions specific to OSPF";
      container config {
        description
          "Configuration parameters for OSPF actions";
        uses ncs_template_ospf-actions-config;
      }
      // NCS drop config false container state
      container set-metric {
        description
          "Configuration and state parameters relating to manipulating
           the OSPF metric";
        container config {
          description
            "Configuration parameters relating to setting the OSPF metric";
          uses ncs_template_ospf-actions-set-metric-config;
        }
        // NCS drop config false container state
      }
    }
  }

  grouping ncs_rpc_notif_ospf-match-config {
    description
      "Configuration parameters for OSPF match conditions";
    leaf area-eq {
      type oc-ospf-types:ncs_rpc_notif_ospf-area-identifier;
      description
        "Match prefixes which are within a particular OSPF area";
    }
  }

  grouping ncs_rpc_notif_ospf-match-conditions {
    description
      "Match conditions that are added by OSPF";
    container ospf-conditions {
      description
        "Match conditions specific to OSPF";
      container config {
        description
          "Configuration parameters relating to OSPF match conditions";
        uses ncs_rpc_notif_ospf-match-config;
      }
      container state {
        config false;
        description
          "Operational state parameters relating to OSPF match conditions";
        uses ncs_rpc_notif_ospf-match-config;
      }
    }
  }

  grouping ncs_rpc_notif_ospf-actions-config {
    description
      "Configuration parameters for OSPF policy actions";
    leaf set-area {
      type oc-ospf-types:ncs_rpc_notif_ospf-area-identifier;
      description
        "Set the area for the matched route. This action is typically
         used when importing prefixes into OSPF, such that a route can
         be imported into a specific area within the instance.";
    }
  }

  grouping ncs_rpc_notif_ospf-actions-set-metric-config {
    description
      "Configuration parameters relating to setting the OSPF metric";
    leaf metric-type {
      type enumeration {
        enum "EXTERNAL_TYPE_1" {
          description
            "Set the external type 1 metric";
        }
        enum "EXTERNAL_TYPE_2" {
          description
            "Set the external type 2 metric";
        }
      }
      default "EXTERNAL_TYPE_2";
      description
        "Specify the type of metric which is to be set by the policy";
    }
    leaf metric {
      type oc-ospf-types:ncs_rpc_notif_ospf-metric;
      description
        "Set the metric of the routes matching the policy to the value
         specified by this leaf.";
    }
  }

  grouping ncs_rpc_notif_ospf-actions {
    description
      "Actions that are added by OSPF to the action framework";
    container ospf-actions {
      description
        "Actions specific to OSPF";
      container config {
        description
          "Configuration parameters for OSPF actions";
        uses ncs_rpc_notif_ospf-actions-config;
      }
      container state {
        config false;
        description
          "Operational state parameters for OSPF actions";
        uses ncs_rpc_notif_ospf-actions-config;
      }
      container set-metric {
        description
          "Configuration and state parameters relating to manipulating
           the OSPF metric";
        container config {
          description
            "Configuration parameters relating to setting the OSPF metric";
          uses ncs_rpc_notif_ospf-actions-set-metric-config;
        }
        container state {
          config false;
          description
            "Operational state parameters relating to setting the OSPF
             metric";
          uses ncs_rpc_notif_ospf-actions-set-metric-config;
        }
      }
    }
  }

  grouping live_ncs_ospf-match-config {
    description
      "Configuration parameters for OSPF match conditions";
    leaf area-eq {
      type oc-ospf-types:live_ncs_ospf-area-identifier;
      description
        "Match prefixes which are within a particular OSPF area";
    }
  }

  grouping live_ncs_ospf-match-conditions {
    description
      "Match conditions that are added by OSPF";
    container ospf-conditions {
      description
        "Match conditions specific to OSPF";
      container config {
        description
          "Configuration parameters relating to OSPF match conditions";
        uses live_ncs_ospf-match-config;
      }
      container state {
        description
          "Operational state parameters relating to OSPF match conditions";
        uses live_ncs_ospf-match-config;
      }
    }
  }

  grouping live_ncs_ospf-actions-config {
    description
      "Configuration parameters for OSPF policy actions";
    leaf set-area {
      type oc-ospf-types:live_ncs_ospf-area-identifier;
      description
        "Set the area for the matched route. This action is typically
         used when importing prefixes into OSPF, such that a route can
         be imported into a specific area within the instance.";
    }
  }

  grouping live_ncs_ospf-actions-set-metric-config {
    description
      "Configuration parameters relating to setting the OSPF metric";
    leaf metric-type {
      type enumeration {
        enum "EXTERNAL_TYPE_1" {
          description
            "Set the external type 1 metric";
        }
        enum "EXTERNAL_TYPE_2" {
          description
            "Set the external type 2 metric";
        }
      }
      // NCS drop default statement
      description
        "Specify the type of metric which is to be set by the policy";
    }
    leaf metric {
      type oc-ospf-types:live_ncs_ospf-metric;
      description
        "Set the metric of the routes matching the policy to the value
         specified by this leaf.";
    }
  }

  grouping live_ncs_ospf-actions {
    description
      "Actions that are added by OSPF to the action framework";
    container ospf-actions {
      description
        "Actions specific to OSPF";
      container config {
        description
          "Configuration parameters for OSPF actions";
        uses live_ncs_ospf-actions-config;
      }
      container state {
        description
          "Operational state parameters for OSPF actions";
        uses live_ncs_ospf-actions-config;
      }
      container set-metric {
        description
          "Configuration and state parameters relating to manipulating
           the OSPF metric";
        container config {
          description
            "Configuration parameters relating to setting the OSPF metric";
          uses live_ncs_ospf-actions-set-metric-config;
        }
        container state {
          description
            "Operational state parameters relating to setting the OSPF
             metric";
          uses live_ncs_ospf-actions-set-metric-config;
        }
      }
    }
  }

  grouping ospf-match-config {
    description
      "Configuration parameters for OSPF match conditions";
    leaf area-eq {
      type oc-ospf-types:ospf-area-identifier;
      description
        "Match prefixes which are within a particular OSPF area";
    }
  }

  grouping ospf-match-conditions {
    description
      "Match conditions that are added by OSPF";
    container ospf-conditions {
      description
        "Match conditions specific to OSPF";
      container config {
        description
          "Configuration parameters relating to OSPF match conditions";
        uses ospf-match-config;
      }
      // NCS drop config false container state
    }
  }

  grouping ospf-actions-config {
    description
      "Configuration parameters for OSPF policy actions";
    leaf set-area {
      type oc-ospf-types:ospf-area-identifier;
      description
        "Set the area for the matched route. This action is typically
         used when importing prefixes into OSPF, such that a route can
         be imported into a specific area within the instance.";
    }
  }

  grouping ospf-actions-set-metric-config {
    description
      "Configuration parameters relating to setting the OSPF metric";
    leaf metric-type {
      type enumeration {
        enum "EXTERNAL_TYPE_1" {
          description
            "Set the external type 1 metric";
        }
        enum "EXTERNAL_TYPE_2" {
          description
            "Set the external type 2 metric";
        }
      }
      default "EXTERNAL_TYPE_2";
      description
        "Specify the type of metric which is to be set by the policy";
    }
    leaf metric {
      type oc-ospf-types:ospf-metric;
      description
        "Set the metric of the routes matching the policy to the value
         specified by this leaf.";
    }
  }

  grouping ospf-actions {
    description
      "Actions that are added by OSPF to the action framework";
    container ospf-actions {
      description
        "Actions specific to OSPF";
      container config {
        description
          "Configuration parameters for OSPF actions";
        uses ospf-actions-config;
      }
      // NCS drop config false container state
      container set-metric {
        description
          "Configuration and state parameters relating to manipulating
           the OSPF metric";
        container config {
          description
            "Configuration parameters relating to setting the OSPF metric";
          uses ospf-actions-set-metric-config;
        }
        // NCS drop config false container state
      }
    }
  }

  augment "/ncs:devices/ncs:template/ncs:ned-id/ncs:config/oc-rpol:routing-policy/oc-rpol:policy-definitions/oc-rpol:policy-definition/oc-rpol:statements/oc-rpol:statement/oc-rpol:conditions" {
    description
      "Add OSPF specific match conditions to the routing policy model";
    uses ncs_template_ospf-match-conditions;
  }
  augment "/ncs:devices/ncs:device/ncs:live-status/oc-rpol:routing-policy/oc-rpol:policy-definitions/oc-rpol:policy-definition/oc-rpol:statements/oc-rpol:statement/oc-rpol:conditions" {
    description
      "Add OSPF specific match conditions to the routing policy model";
    uses live_ncs_ospf-match-conditions {
      refine ospf-conditions {
        tailf:ncs-device-type "netconf";
        tailf:display-when "not(../../../../../../../../ncs:module) or ../../../../../../../../ncs:module[ncs:name='openconfig-ospf-policy'] or (../../../../../../../../ncs:live-status-protocol[not(ncs:capability)]) or (../../../../../../../../ncs:live-status-protocol/ncs:capability/ncs:module[.='openconfig-ospf-policy'])";
      }
    }
  }
  augment "/ncs:devices/ncs:device/ncs:config/oc-rpol:routing-policy/oc-rpol:policy-definitions/oc-rpol:policy-definition/oc-rpol:statements/oc-rpol:statement/oc-rpol:conditions" {
    description
      "Add OSPF specific match conditions to the routing policy model";
    uses ospf-match-conditions {
      refine ospf-conditions {
        tailf:ncs-device-type "netconf";
        tailf:display-when "not(../../../../../../../../ncs:module) or ../../../../../../../../ncs:module[ncs:name='openconfig-ospf-policy']";
      }
    }
  }
  augment "/ncs:devices/ncs:template/ncs:ned-id/ncs:config/oc-rpol:routing-policy/oc-rpol:policy-definitions/oc-rpol:policy-definition/oc-rpol:statements/oc-rpol:statement/oc-rpol:actions" {
    description
      "Add OSPF specific actions to the routing policy model";
    uses ncs_template_ospf-actions;
  }
  augment "/ncs:devices/ncs:device/ncs:live-status/oc-rpol:routing-policy/oc-rpol:policy-definitions/oc-rpol:policy-definition/oc-rpol:statements/oc-rpol:statement/oc-rpol:actions" {
    description
      "Add OSPF specific actions to the routing policy model";
    uses live_ncs_ospf-actions {
      refine ospf-actions {
        tailf:ncs-device-type "netconf";
        tailf:display-when "not(../../../../../../../../ncs:module) or ../../../../../../../../ncs:module[ncs:name='openconfig-ospf-policy'] or (../../../../../../../../ncs:live-status-protocol[not(ncs:capability)]) or (../../../../../../../../ncs:live-status-protocol/ncs:capability/ncs:module[.='openconfig-ospf-policy'])";
      }
    }
  }
  augment "/ncs:devices/ncs:device/ncs:config/oc-rpol:routing-policy/oc-rpol:policy-definitions/oc-rpol:policy-definition/oc-rpol:statements/oc-rpol:statement/oc-rpol:actions" {
    description
      "Add OSPF specific actions to the routing policy model";
    uses ospf-actions {
      refine ospf-actions {
        tailf:ncs-device-type "netconf";
        tailf:display-when "not(../../../../../../../../ncs:module) or ../../../../../../../../ncs:module[ncs:name='openconfig-ospf-policy']";
      }
    }
  }
}
