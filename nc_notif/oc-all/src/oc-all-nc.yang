module oc-all-nc {
  yang-version 1.1;
  namespace "http://tail-f.com/ns/ned-id/oc-all-nc";
  prefix oc-all-nc;

  import tailf-common {
    prefix tailf;
  }

  import tailf-ncs-ned {
    prefix ned;
  }

  identity oc-all-nc {
    tailf:abstract;
    base ned:netconf-ned-id;
  }
}
