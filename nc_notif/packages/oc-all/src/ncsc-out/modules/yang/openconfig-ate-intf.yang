module openconfig-ate-intf {
  // Generated by yanger -t ncs
  tailf:mount-id "oc-all-nc-1.0:oc-all-nc-1.0";
  tailf:ncs-device-type "netconf";

  yang-version 1;
  namespace "http://openconfig.net/yang/ate-intf";
  prefix oc-atei;

  import openconfig-extensions {
    prefix oc-ext;
  }
  import openconfig-types {
    prefix oc-types;
  }
  import openconfig-interfaces {
    prefix oc-if;
  }
  import tailf-common {
    prefix tailf;
  }
  import tailf-ncs {
    prefix ncs;
  }

  organization
    "OpenConfig working group";
  contact
    "OpenConfig working group
     netopenconfig@googlegroups.com";
  description
    "This module defines augments to the OpenConfig tree specifically for
     automated test equipment (ATE) devices. These parameters are not widely
     supported by non-ATE devices.";
  oc-ext:openconfig-version "0.1.0";

  revision 2019-08-07 {
    description
      "Initial revision.";
    reference "0.1.0";
  }
  oc-ext:regexp-posix;
  oc-ext:catalog-organization "openconfig";
  oc-ext:origin "openconfig";

  grouping ncs_template_interface-rate {
    description
      "Calculated rate parameters for interfaces supported directly by
       ATE devices.";
    leaf out-rate {
      type oc-types:ncs_template_ieeefloat32;
      units "bps";
      description
        "The calculated transmitted rate of the interface, measured in bits
         per second.";
    }
    leaf in-rate {
      type oc-types:ncs_template_ieeefloat32;
      units "bps";
      description
        "The calculate received rate of the interface, measured in bits
         per second.";
    }
  }

  grouping ncs_rpc_notif_interface-rate {
    description
      "Calculated rate parameters for interfaces supported directly by
       ATE devices.";
    leaf out-rate {
      type oc-types:ncs_rpc_notif_ieeefloat32;
      units "bps";
      description
        "The calculated transmitted rate of the interface, measured in bits
         per second.";
    }
    leaf in-rate {
      type oc-types:ncs_rpc_notif_ieeefloat32;
      units "bps";
      description
        "The calculate received rate of the interface, measured in bits
         per second.";
    }
  }

  grouping live_ncs_interface-rate {
    description
      "Calculated rate parameters for interfaces supported directly by
       ATE devices.";
    leaf out-rate {
      type oc-types:live_ncs_ieeefloat32;
      units "bps";
      description
        "The calculated transmitted rate of the interface, measured in bits
         per second.";
    }
    leaf in-rate {
      type oc-types:live_ncs_ieeefloat32;
      units "bps";
      description
        "The calculate received rate of the interface, measured in bits
         per second.";
    }
  }

  grouping interface-rate {
    description
      "Calculated rate parameters for interfaces supported directly by
       ATE devices.";
    leaf out-rate {
      type oc-types:ieeefloat32;
      units "bps";
      description
        "The calculated transmitted rate of the interface, measured in bits
         per second.";
    }
    leaf in-rate {
      type oc-types:ieeefloat32;
      units "bps";
      description
        "The calculate received rate of the interface, measured in bits
         per second.";
    }
  }

  augment "/ncs:devices/ncs:device/ncs:live-status/oc-if:interfaces/oc-if:interface/oc-if:state" {
    description
      "Augment the OpenConfig interfaces base model with ATE specific
       state parameters.";
    uses live_ncs_interface-rate {
      refine in-rate {
        tailf:ncs-device-type "netconf";
        tailf:display-when "not(../../../../../ncs:module) or ../../../../../ncs:module[ncs:name='openconfig-ate-intf'] or (../../../../../ncs:live-status-protocol[not(ncs:capability)]) or (../../../../../ncs:live-status-protocol/ncs:capability/ncs:module[.='openconfig-ate-intf'])";
      }
      refine out-rate {
        tailf:ncs-device-type "netconf";
        tailf:display-when "not(../../../../../ncs:module) or ../../../../../ncs:module[ncs:name='openconfig-ate-intf'] or (../../../../../ncs:live-status-protocol[not(ncs:capability)]) or (../../../../../ncs:live-status-protocol/ncs:capability/ncs:module[.='openconfig-ate-intf'])";
      }
    }
  }
}
