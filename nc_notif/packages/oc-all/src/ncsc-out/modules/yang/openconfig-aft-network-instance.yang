module openconfig-aft-network-instance {
  // Generated by yanger -t ncs
  tailf:mount-id "oc-all-nc-1.0:oc-all-nc-1.0";
  tailf:ncs-device-type "netconf";

  yang-version 1;
  namespace "http://openconfig.net/yang/aft/ni";
  prefix oc-aftni;

  import openconfig-extensions {
    prefix oc-ext;
  }
  import openconfig-network-instance {
    prefix oc-ni;
  }
  import tailf-common {
    prefix tailf;
  }
  import tailf-ncs {
    prefix ncs;
  }

  organization
    "OpenConfig working group";
  contact
    "OpenConfig working group
     www.openconfig.net";
  description
    "This module provides augmentations that are utilized
     when building the OpenConfig network instance model to
     add per-NI AFTs.";
  oc-ext:openconfig-version "0.3.0";

  revision 2022-03-29 {
    description
      "Relocate next-hop-group/next-hop-group-network-instance
       from openconfig-aft-common to resolve absolute path
       leafref specific to network-instances";
    reference "0.3.0";
  }
  revision 2018-11-21 {
    description
      "Add OpenConfig module metadata extensions.";
    reference "0.2.3";
  }
  revision 2017-08-24 {
    description
      "Formatting fixes";
    reference "0.2.2";
  }
  revision 2017-01-13 {
    description
      "Updated revision for external review";
    reference "0.2.1";
  }
  oc-ext:regexp-posix;
  oc-ext:catalog-organization "openconfig";
  oc-ext:origin "openconfig";

  grouping ncs_template_aft-nexthop-ni-state {
    description
      "Operational state parameters relating to a next-hop which reference a
       network instance.";
    leaf network-instance {
      type oc-ni:ncs_template_network-instance-ref;
      description
        "The network-instance within which the next-hop should be resolved.
         When this leaf is unspecified, the next-hop is resolved within
         the local instance.";
    }
  }

  grouping ncs_template_aft-entry-ni-state {
    description
      "Operational state parameters relating to an AFT entry which reference
       a network instance.";
    leaf origin-network-instance {
      type oc-ni:ncs_template_network-instance-ref;
      description
        "If the AFT entry was imported from another network instance (e.g., it
         corresponds to a L3 forwarding entry which was learned within another
         network-instance), the value of this leaf reflects the network-instance
         from which it was learned.

         For example, if the local network-instance corresponds to a L3VRF, and
         routes are imported from the VPNv4 address-family of the BGP instance
         in the DEFAULT_INSTANCE, then this value would reflect the
         DEFAULT_INSTANCE as the origin-network-instance.";
    }
  }

  grouping ncs_template_aft-entry-nexthop-group-state {
    description
      "Operational state nexthop group parameters relating to an AFT entry
       which reference a network instance.";
    leaf next-hop-group {
      type string;
      description
        "A reference to the next-hop-group that is in use for the entry within
         the AFT. Traffic is distributed across the set of next-hops within the
         next-hop group according to the weight. This node needs to refer to any
         network-instance on the system hence must be absolute.";
    }
    leaf next-hop-group-network-instance {
      type oc-ni:ncs_template_network-instance-ref;
      description
        "The network instance to look up the next-hop-group in. If unspecified,
         the next hop group is in the local network instance. The referenced
         network-instance must be an existing network instance on the device and
         have corresponding entries in the /network-instances/network-instance
         list.";
    }
  }

  grouping ncs_rpc_notif_aft-nexthop-ni-state {
    description
      "Operational state parameters relating to a next-hop which reference a
       network instance.";
    leaf network-instance {
      type oc-ni:ncs_rpc_notif_network-instance-ref;
      description
        "The network-instance within which the next-hop should be resolved.
         When this leaf is unspecified, the next-hop is resolved within
         the local instance.";
    }
  }

  grouping ncs_rpc_notif_aft-entry-ni-state {
    description
      "Operational state parameters relating to an AFT entry which reference
       a network instance.";
    leaf origin-network-instance {
      type oc-ni:ncs_rpc_notif_network-instance-ref;
      description
        "If the AFT entry was imported from another network instance (e.g., it
         corresponds to a L3 forwarding entry which was learned within another
         network-instance), the value of this leaf reflects the network-instance
         from which it was learned.

         For example, if the local network-instance corresponds to a L3VRF, and
         routes are imported from the VPNv4 address-family of the BGP instance
         in the DEFAULT_INSTANCE, then this value would reflect the
         DEFAULT_INSTANCE as the origin-network-instance.";
    }
  }

  grouping ncs_rpc_notif_aft-entry-nexthop-group-state {
    description
      "Operational state nexthop group parameters relating to an AFT entry
       which reference a network instance.";
    leaf next-hop-group {
      type string;
      description
        "A reference to the next-hop-group that is in use for the entry within
         the AFT. Traffic is distributed across the set of next-hops within the
         next-hop group according to the weight. This node needs to refer to any
         network-instance on the system hence must be absolute.";
    }
    leaf next-hop-group-network-instance {
      type oc-ni:ncs_rpc_notif_network-instance-ref;
      description
        "The network instance to look up the next-hop-group in. If unspecified,
         the next hop group is in the local network instance. The referenced
         network-instance must be an existing network instance on the device and
         have corresponding entries in the /network-instances/network-instance
         list.";
    }
  }

  grouping live_ncs_aft-nexthop-ni-state {
    description
      "Operational state parameters relating to a next-hop which reference a
       network instance.";
    leaf network-instance {
      type oc-ni:live_ncs_network-instance-ref;
      description
        "The network-instance within which the next-hop should be resolved.
         When this leaf is unspecified, the next-hop is resolved within
         the local instance.";
    }
  }

  grouping live_ncs_aft-entry-ni-state {
    description
      "Operational state parameters relating to an AFT entry which reference
       a network instance.";
    leaf origin-network-instance {
      type oc-ni:live_ncs_network-instance-ref;
      description
        "If the AFT entry was imported from another network instance (e.g., it
         corresponds to a L3 forwarding entry which was learned within another
         network-instance), the value of this leaf reflects the network-instance
         from which it was learned.

         For example, if the local network-instance corresponds to a L3VRF, and
         routes are imported from the VPNv4 address-family of the BGP instance
         in the DEFAULT_INSTANCE, then this value would reflect the
         DEFAULT_INSTANCE as the origin-network-instance.";
    }
  }

  grouping live_ncs_aft-entry-nexthop-group-state {
    description
      "Operational state nexthop group parameters relating to an AFT entry
       which reference a network instance.";
    leaf next-hop-group {
      type leafref {
        path "/ncs:devices/ncs:device/ncs:live-status/oc-ni:network-instances/oc-ni:network-instance/oc-ni:afts/oc-ni:next-hop-groups/oc-ni:next-hop-group/oc-ni:state/oc-ni:id" {
          tailf:xpath-root 3;
        }
      }
      description
        "A reference to the next-hop-group that is in use for the entry within
         the AFT. Traffic is distributed across the set of next-hops within the
         next-hop group according to the weight. This node needs to refer to any
         network-instance on the system hence must be absolute.";
    }
    leaf next-hop-group-network-instance {
      type oc-ni:live_ncs_network-instance-ref;
      description
        "The network instance to look up the next-hop-group in. If unspecified,
         the next hop group is in the local network instance. The referenced
         network-instance must be an existing network instance on the device and
         have corresponding entries in the /network-instances/network-instance
         list.";
    }
  }

  grouping aft-nexthop-ni-state {
    description
      "Operational state parameters relating to a next-hop which reference a
       network instance.";
    leaf network-instance {
      type oc-ni:network-instance-ref;
      description
        "The network-instance within which the next-hop should be resolved.
         When this leaf is unspecified, the next-hop is resolved within
         the local instance.";
    }
  }

  grouping aft-entry-ni-state {
    description
      "Operational state parameters relating to an AFT entry which reference
       a network instance.";
    leaf origin-network-instance {
      type oc-ni:network-instance-ref;
      description
        "If the AFT entry was imported from another network instance (e.g., it
         corresponds to a L3 forwarding entry which was learned within another
         network-instance), the value of this leaf reflects the network-instance
         from which it was learned.

         For example, if the local network-instance corresponds to a L3VRF, and
         routes are imported from the VPNv4 address-family of the BGP instance
         in the DEFAULT_INSTANCE, then this value would reflect the
         DEFAULT_INSTANCE as the origin-network-instance.";
    }
  }

  grouping aft-entry-nexthop-group-state {
    description
      "Operational state nexthop group parameters relating to an AFT entry
       which reference a network instance.";
    leaf next-hop-group {
      type leafref {
        path "/ncs:devices/ncs:device/ncs:live-status/oc-ni:network-instances/oc-ni:network-instance/oc-ni:afts/oc-ni:next-hop-groups/oc-ni:next-hop-group/oc-ni:state/oc-ni:id" {
          tailf:xpath-root 2;
        }
      }
      description
        "A reference to the next-hop-group that is in use for the entry within
         the AFT. Traffic is distributed across the set of next-hops within the
         next-hop group according to the weight. This node needs to refer to any
         network-instance on the system hence must be absolute.";
    }
    leaf next-hop-group-network-instance {
      type oc-ni:network-instance-ref;
      description
        "The network instance to look up the next-hop-group in. If unspecified,
         the next hop group is in the local network instance. The referenced
         network-instance must be an existing network instance on the device and
         have corresponding entries in the /network-instances/network-instance
         list.";
    }
  }

  augment "/ncs:devices/ncs:device/ncs:live-status/oc-ni:network-instances/oc-ni:network-instance/oc-ni:afts/oc-ni:next-hops/oc-ni:next-hop/oc-ni:state" {
    description
      "Add leaves that require referencing of a network instance to the
       operational state parameters of a next-hop within the AFT for IPv4
       unicast.";
    uses live_ncs_aft-nexthop-ni-state {
      refine network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
  augment "/ncs:devices/ncs:device/ncs:live-status/oc-ni:network-instances/oc-ni:network-instance/oc-ni:afts/oc-ni:ipv4-unicast/oc-ni:ipv4-entry/oc-ni:state" {
    description
      "Add leaves that require referencing of a network instance to the
       operational state parameters of an entry within the IPv4 unicast AFT.";
    uses live_ncs_aft-entry-nexthop-group-state {
      refine next-hop-group-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
      refine next-hop-group {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
    uses live_ncs_aft-entry-ni-state {
      refine origin-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
  augment "/ncs:devices/ncs:device/ncs:live-status/oc-ni:network-instances/oc-ni:network-instance/oc-ni:afts/oc-ni:ipv6-unicast/oc-ni:ipv6-entry/oc-ni:state" {
    description
      "Add leaves that require referencing of a network instance to the
       operational state parameters of an entry within the IPv6 unicast AFT.";
    uses live_ncs_aft-entry-nexthop-group-state {
      refine next-hop-group-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
      refine next-hop-group {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
    uses live_ncs_aft-entry-ni-state {
      refine origin-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
  augment "/ncs:devices/ncs:device/ncs:live-status/oc-ni:network-instances/oc-ni:network-instance/oc-ni:afts/oc-ni:policy-forwarding/oc-ni:policy-forwarding-entry/oc-ni:state" {
    description
      "Add leaves that require referencing of a network instance to the
       operational state parameters of an entry within the Policy Forwarding
       AFT.";
    uses live_ncs_aft-entry-nexthop-group-state {
      refine next-hop-group-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
      refine next-hop-group {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
  augment "/ncs:devices/ncs:device/ncs:live-status/oc-ni:network-instances/oc-ni:network-instance/oc-ni:afts/oc-ni:mpls/oc-ni:label-entry/oc-ni:state" {
    description
      "Add leaves that require referencing of a network instance to the
       operational state parameters of an entry within the MPLS AFT.";
    uses live_ncs_aft-entry-nexthop-group-state {
      refine next-hop-group-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
      refine next-hop-group {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
  augment "/ncs:devices/ncs:device/ncs:live-status/oc-ni:network-instances/oc-ni:network-instance/oc-ni:afts/oc-ni:ethernet/oc-ni:mac-entry/oc-ni:state" {
    description
      "Add leaves that require referencing of a network instance to the
       operational state parameters of an entry within the Ethernet AFT.";
    uses live_ncs_aft-entry-nexthop-group-state {
      refine next-hop-group-network-instance {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
      refine next-hop-group {
        tailf:ncs-device-type "netconf";
        tailf:display-when "not(../../../../../../../../ncs:module) or ../../../../../../../../ncs:module[ncs:name='openconfig-aft-network-instance'] or (../../../../../../../../ncs:live-status-protocol[not(ncs:capability)]) or (../../../../../../../../ncs:live-status-protocol/ncs:capability/ncs:module[.='openconfig-aft-network-instance'])";
      }
    }
  }
}
