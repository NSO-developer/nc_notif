module openconfig-platform-psu {
  // Generated by yanger -t ncs
  tailf:mount-id "oc-all-nc-1.0:oc-all-nc-1.0";
  tailf:ncs-device-type "netconf";

  yang-version 1;
  namespace "http://openconfig.net/yang/platform/psu";
  prefix oc-platform-psu;

  import openconfig-extensions {
    prefix oc-ext;
  }
  import openconfig-types {
    prefix oc-types;
  }
  import openconfig-platform {
    prefix oc-platform;
  }
  import tailf-common {
    prefix tailf;
  }
  import tailf-ncs {
    prefix ncs;
  }

  organization
    "OpenConfig working group";
  contact
    "OpenConfig working group
     www.openconfig.net";
  description
    "This module defines a schema for power supply components in
     the OpenConfig platform model.";
  oc-ext:openconfig-version "0.2.1";

  revision 2018-11-21 {
    description
      "Add OpenConfig module metadata extensions.";
    reference "0.2.1";
  }
  revision 2018-01-16 {
    description
      "Changed admin state leaf name";
    reference "0.2.0";
  }
  revision 2017-12-21 {
    description
      "Initial revision";
    reference "0.1.0";
  }
  oc-ext:regexp-posix;
  oc-ext:catalog-organization "openconfig";
  oc-ext:origin "openconfig";

  grouping ncs_template_psu-config {
    description
      "Configuration data for power supply components";
    leaf enabled {
      type string;
      // NCS drop default statement
      description
        "Adminsitrative control on the on/off state of the power
         supply unit.";
    }
  }

  grouping ncs_template_psu-state {
    description
      "Operational state data for power supply components";
    leaf capacity {
      type oc-types:ncs_template_ieeefloat32;
      units "watts";
      description
        "Maximum power capacity of the power supply.";
    }
    leaf input-current {
      type oc-types:ncs_template_ieeefloat32;
      units "amps";
      description
        "The input current draw of the power supply.";
    }
    leaf input-voltage {
      type oc-types:ncs_template_ieeefloat32;
      units "volts";
      description
        "Input voltage to the power supply.";
    }
    leaf output-current {
      type oc-types:ncs_template_ieeefloat32;
      units "amps";
      description
        "The output current supplied by the power supply.";
    }
    leaf output-voltage {
      type oc-types:ncs_template_ieeefloat32;
      units "volts";
      description
        "Output voltage supplied by the power supply.";
    }
    leaf output-power {
      type oc-types:ncs_template_ieeefloat32;
      units "watts";
      description
        "Output power supplied by the power supply.";
    }
  }

  grouping ncs_rpc_notif_psu-config {
    description
      "Configuration data for power supply components";
    leaf enabled {
      type boolean;
      default "true";
      description
        "Adminsitrative control on the on/off state of the power
         supply unit.";
    }
  }

  grouping ncs_rpc_notif_psu-state {
    description
      "Operational state data for power supply components";
    leaf capacity {
      type oc-types:ncs_rpc_notif_ieeefloat32;
      units "watts";
      description
        "Maximum power capacity of the power supply.";
    }
    leaf input-current {
      type oc-types:ncs_rpc_notif_ieeefloat32;
      units "amps";
      description
        "The input current draw of the power supply.";
    }
    leaf input-voltage {
      type oc-types:ncs_rpc_notif_ieeefloat32;
      units "volts";
      description
        "Input voltage to the power supply.";
    }
    leaf output-current {
      type oc-types:ncs_rpc_notif_ieeefloat32;
      units "amps";
      description
        "The output current supplied by the power supply.";
    }
    leaf output-voltage {
      type oc-types:ncs_rpc_notif_ieeefloat32;
      units "volts";
      description
        "Output voltage supplied by the power supply.";
    }
    leaf output-power {
      type oc-types:ncs_rpc_notif_ieeefloat32;
      units "watts";
      description
        "Output power supplied by the power supply.";
    }
  }

  grouping live_ncs_psu-config {
    description
      "Configuration data for power supply components";
    leaf enabled {
      type boolean;
      // NCS drop default statement
      description
        "Adminsitrative control on the on/off state of the power
         supply unit.";
    }
  }

  grouping live_ncs_psu-state {
    description
      "Operational state data for power supply components";
    leaf capacity {
      type oc-types:live_ncs_ieeefloat32;
      units "watts";
      description
        "Maximum power capacity of the power supply.";
    }
    leaf input-current {
      type oc-types:live_ncs_ieeefloat32;
      units "amps";
      description
        "The input current draw of the power supply.";
    }
    leaf input-voltage {
      type oc-types:live_ncs_ieeefloat32;
      units "volts";
      description
        "Input voltage to the power supply.";
    }
    leaf output-current {
      type oc-types:live_ncs_ieeefloat32;
      units "amps";
      description
        "The output current supplied by the power supply.";
    }
    leaf output-voltage {
      type oc-types:live_ncs_ieeefloat32;
      units "volts";
      description
        "Output voltage supplied by the power supply.";
    }
    leaf output-power {
      type oc-types:live_ncs_ieeefloat32;
      units "watts";
      description
        "Output power supplied by the power supply.";
    }
  }

  grouping psu-config {
    description
      "Configuration data for power supply components";
    leaf enabled {
      type boolean;
      default "true";
      description
        "Adminsitrative control on the on/off state of the power
         supply unit.";
    }
  }

  grouping psu-state {
    description
      "Operational state data for power supply components";
    leaf capacity {
      type oc-types:ieeefloat32;
      units "watts";
      description
        "Maximum power capacity of the power supply.";
    }
    leaf input-current {
      type oc-types:ieeefloat32;
      units "amps";
      description
        "The input current draw of the power supply.";
    }
    leaf input-voltage {
      type oc-types:ieeefloat32;
      units "volts";
      description
        "Input voltage to the power supply.";
    }
    leaf output-current {
      type oc-types:ieeefloat32;
      units "amps";
      description
        "The output current supplied by the power supply.";
    }
    leaf output-voltage {
      type oc-types:ieeefloat32;
      units "volts";
      description
        "Output voltage supplied by the power supply.";
    }
    leaf output-power {
      type oc-types:ieeefloat32;
      units "watts";
      description
        "Output power supplied by the power supply.";
    }
  }

  augment "/ncs:devices/ncs:template/ncs:ned-id/ncs:config/oc-platform:components/oc-platform:component/oc-platform:power-supply/oc-platform:config" {
    description
      "Adds power supply data to component operational state.";
    uses ncs_template_psu-config;
  }
  augment "/ncs:devices/ncs:device/ncs:live-status/oc-platform:components/oc-platform:component/oc-platform:power-supply/oc-platform:config" {
    description
      "Adds power supply data to component operational state.";
    uses live_ncs_psu-config {
      refine enabled {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
    }
  }
  augment "/ncs:devices/ncs:device/ncs:config/oc-platform:components/oc-platform:component/oc-platform:power-supply/oc-platform:config" {
    description
      "Adds power supply data to component operational state.";
    uses psu-config {
      refine enabled {
        tailf:ncs-device-type "netconf";
        tailf:display-when "not(../../../../../../ncs:module) or ../../../../../../ncs:module[ncs:name='openconfig-platform-psu']";
      }
    }
  }
  augment "/ncs:devices/ncs:device/ncs:live-status/oc-platform:components/oc-platform:component/oc-platform:power-supply/oc-platform:state" {
    description
      "Adds power supply data to component operational state.";
    uses live_ncs_psu-config {
      refine enabled {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
    }
    uses live_ncs_psu-state {
      refine output-power {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
      refine output-voltage {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
      refine output-current {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
      refine input-voltage {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
      refine input-current {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
      refine capacity {
        tailf:ncs-device-type "netconf";
        tailf:display-when "not(../../../../../../ncs:module) or ../../../../../../ncs:module[ncs:name='openconfig-platform-psu'] or (../../../../../../ncs:live-status-protocol[not(ncs:capability)]) or (../../../../../../ncs:live-status-protocol/ncs:capability/ncs:module[.='openconfig-platform-psu'])";
      }
    }
  }
}
