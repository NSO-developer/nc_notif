module openconfig-probes {
  // Generated by yanger -t ncs
  tailf:mount-id "oc-all-nc-1.0:oc-all-nc-1.0";
  tailf:ncs-device-type "netconf";

  yang-version 1;
  namespace "http://openconfig.net/yang/probes";
  prefix oc-probes;

  import ietf-yang-types {
    prefix yang;
  }
  import openconfig-types {
    prefix oc-types;
  }
  import openconfig-extensions {
    prefix oc-ext;
  }
  import openconfig-inet-types {
    prefix oc-inet;
  }
  import openconfig-probes-types {
    prefix oc-probes-types;
  }
  import tailf-common {
    prefix tailf;
  }
  import tailf-ncs {
    prefix ncs;
  }

  organization
    "OpenConfig working group";
  contact
    "OpenConfig working group
     www.openconfig.net";
  description
    "This module defines configuration and operational state data
     for the probes.
     A probe consists on a group of tests, each test being a
     source-destination pair to poll. The destination can be either
     IP Address (and eventually port) or URL, depending on the
     nature of the test. The test can send ICMP, UDP, TCP, or HTTP
     requests.
     Each test groups a list of test items, the test results
     being an overall view or average of the items list.
     However, the test preserves only a limited set of history
     items, whose length can be controlled using the history-size.";
  oc-ext:openconfig-version "0.0.2";

  revision 2018-11-21 {
    description
      "Add OpenConfig module metadata extensions.";
    reference "0.0.2";
  }
  revision 2017-09-05 {
    description
      "Initial public revision";
    reference "0.0.1";
  }
  oc-ext:regexp-posix;
  oc-ext:catalog-organization "openconfig";
  oc-ext:origin "openconfig";

  grouping ncs_template_test-target {
    description
      "Groups the config and state containers
       for an individual test.";
    container target {
      description
        "The target configuration of the test.
         The nature of the target depends on the probe type:
         for HTTP probes we need to provide an URL to poll,
         while ICMP probes require an IP address to monitor.";
      container config {
        description
          "Configuration data for the test target.";
        uses ncs_template_test-target-base;
      }
      // NCS drop config false container state
    }
  }

  grouping ncs_template_test-target-base {
    description
      "Targe types for the probe test.";
    leaf address {
      type oc-inet:ncs_template_ip-address;
      description
        "IP address of the target, either IPv4 or IPv6.";
    }
    leaf port {
      type oc-inet:ncs_template_port-number;
      description
        "Destination port.";
    }
    leaf url {
      type oc-inet:ncs_template_url;
      description
        "Target URL to probe.";
    }
  }

  grouping ncs_template_probe-test-config-base {
    description
      "Definition of test details.";
    leaf test-type {
      type oc-probes-types:ncs_template_test-type;
      description
        "The type of the probe test.";
      // NCS drop mandatory statement
    }
    leaf count {
      type string;
      description
        "The number of probes per test.";
    }
    leaf interval {
      type string;
      description
        "Time between two consecutive probes.";
    }
    leaf source {
      type oc-inet:ncs_template_ip-address;
      description
        "Source address used when probing, either IPv4 or IPv6.";
    }
    leaf history-size {
      type string;
      description
        "The number of history entries stored.";
    }
    leaf source-port {
      type oc-inet:ncs_template_port-number;
      description
        "Source number used.";
    }
    leaf dscp {
      type oc-inet:ncs_template_dscp;
      description
        "DSCP code points";
    }
  }

  grouping ncs_template_probe-test-state-history-item-base {
    description
      "The test item results counters and statistics.
       An item presents the results of a single execution
       of the test.
       The results of the test depend on the values
       of the total items, or an average over a certain
       period of time.";
    leaf id {
      type string;
      description
        "The test item ID.";
    }
    leaf timestamp {
      type oc-types:ncs_template_timeticks64;
      description
        "The test timestamp.
         This is not the timestamp when the test
         was actually executed nither when it finished.
         Should be the timestamp when the test has been scheduled.
         It may not be the same with start-timestamp.";
    }
    leaf start-timestamp {
      type oc-types:ncs_template_timeticks64;
      description
        "The timestamp when the test started.";
    }
    leaf end-timestamp {
      type oc-types:ncs_template_timeticks64;
      description
        "The timestamp when the test finished.";
    }
    leaf test-duration {
      type string;
      description
        "The duration of the test, in microseconds.";
    }
    leaf failed {
      type string;
      description
        "Whether the test failed or succeeded.";
    }
    leaf probes-sent {
      type string;
      description
        "Number of test probes sent.";
    }
    leaf probes-received {
      type string;
      description
        "Number of test probes received.";
    }
    leaf loss-percentage {
      type oc-types:ncs_template_percentage;
      description
        "The loss percentage.";
    }
    leaf jitter {
      type string;
      description
        "The round trip jitter, in microseconds.";
    }
    leaf min-delay {
      type string;
      description
        "The minimum delay recorded during the test, in microseconds.";
    }
    leaf max-delay {
      type string;
      description
        "The maximum delay recorded during the test, in microseconds.";
    }
    leaf avg-delay {
      type string;
      description
        "The average delay recorded during the test, in microseconds.";
    }
    leaf stddev-delay {
      type string;
      description
        "The standard deviation of the delay of the test.";
    }
  }

  grouping ncs_template_probe-test-state-history-item {
    description
      "A history item of the probe results.";
    // NCS drop config false container state
  }

  grouping ncs_template_probe-test-state-history {
    description
      "The history of the test results.";
    container items {
      description
        "The list of items in the probe history.
         The length depends on the history size.";
      list item {
        // NCS patched for predictable order
        ordered-by user;
        key "id";
        description
          "List of history items.";
        leaf id {
          type string;
          description
            "Reference to the history entry ID.";
        }
        uses ncs_template_probe-test-state-history-item;
      }
    }
  }

  grouping ncs_template_probe-test-state-results {
    description
      "The test results counters and statistics.";
    leaf timestamp {
      type oc-types:ncs_template_timeticks64;
      description
        "The test timestamp.
         This is not the timestamp when the test
         was actually executed nither when it finished.
         Should be the timestamp when the test has been scheduled.
         It may not be the same with start-timestamp.";
    }
    leaf start-timestamp {
      type oc-types:ncs_template_timeticks64;
      description
        "The timestamp when the test started.";
    }
    leaf last-test-timestamp {
      type oc-types:ncs_template_timeticks64;
      description
        "The timestamp when the test finished.";
    }
    leaf test-duration {
      type string;
      description
        "The duration of the test, in microseconds.";
    }
    leaf failed {
      type string;
      description
        "Whether the test failed or succeeded.";
    }
    leaf probes-sent {
      type string;
      description
        "Number of test probes sent.";
    }
    leaf probes-received {
      type string;
      description
        "Number of test probes received.";
    }
    leaf loss-percentage {
      type oc-types:ncs_template_percentage;
      description
        "The loss percentage.";
    }
    leaf jitter {
      type string;
      description
        "The round trip jitter, in microseconds.";
    }
    leaf min-delay {
      type string;
      description
        "The minimum delay recorded during the test, in microseconds.";
    }
    leaf max-delay {
      type string;
      description
        "The maximum delay recorded during the test, in microseconds.";
    }
    leaf avg-delay {
      type string;
      description
        "The average delay recorded during the test, in microseconds.";
    }
    leaf stddev-delay {
      type string;
      description
        "The standard deviation of the delay of the test.";
    }
  }

  grouping ncs_template_probe-test-state {
    description
      "Operational data and results for the probes.";
  }

  grouping ncs_template_probe-test-config {
    description
      "Definition of test details.";
    leaf name {
      type string;
      description
        "The name of the test probe";
      // NCS drop mandatory statement
    }
    leaf enabled {
      type string;
      // NCS drop default statement
      description
        "Whether the test is enabled.";
    }
    uses ncs_template_probe-test-config-base;
  }

  grouping ncs_template_probe-tests-top {
    description
      "Top-level grouping for the tests withing a probe.";
    list test {
      // NCS patched for predictable order
      ordered-by user;
      key "name";
      description
        "List of tests associated with this probe.";
      leaf name {
        type string;
        description
          "Reference to the list key";
      }
      container config {
        description
          "Configuration data for the test of this probe.";
        uses ncs_template_probe-test-config;
      }
      // NCS drop config false container state
      uses ncs_template_test-target;
      container results {
        description
          "Contains the results of the tests.";
        // NCS drop config false container state
        // NCS drop config false container history
      }
    }
  }

  grouping ncs_template_probe-config {
    description
      "Definition of probe details.";
    leaf name {
      type string;
      description
        "The name of the probe.";
      // NCS drop mandatory statement
    }
    leaf enabled {
      type string;
      // NCS drop default statement
      description
        "Whether the probe is enabled.";
    }
  }

  grouping ncs_template_probe-state {
    description
      "Definition of probes operation data.";
  }

  grouping ncs_template_probes-top {
    description
      "Top-level grouping for probes model";
    list probe {
      // NCS patched for predictable order
      ordered-by user;
      key "name";
      description
        "List of probes configured.";
      leaf name {
        type string;
        description
          "Reference to the list key";
      }
      container config {
        description
          "Configuration data for the probes.";
        uses ncs_template_probe-config;
      }
      // NCS drop config false container state
      container tests {
        description
          "The tests associated to be executed for the probe.";
        uses ncs_template_probe-tests-top;
      }
    }
  }

  grouping ncs_template_openconfig-probes-top {
    description
      "The top level grouping of the probes model.";
    container probes {
      description
        "The container containing the list of probes.";
      uses ncs_template_probes-top;
    }
  }

  grouping ncs_rpc_notif_test-target {
    description
      "Groups the config and state containers
       for an individual test.";
    container target {
      description
        "The target configuration of the test.
         The nature of the target depends on the probe type:
         for HTTP probes we need to provide an URL to poll,
         while ICMP probes require an IP address to monitor.";
      container config {
        description
          "Configuration data for the test target.";
        uses ncs_rpc_notif_test-target-base;
      }
      container state {
        config false;
        description
          "Operational data for the test target.";
        uses ncs_rpc_notif_test-target-base;
      }
    }
  }

  grouping ncs_rpc_notif_test-target-base {
    description
      "Targe types for the probe test.";
    leaf address {
      type oc-inet:ncs_rpc_notif_ip-address;
      description
        "IP address of the target, either IPv4 or IPv6.";
    }
    leaf port {
      type oc-inet:ncs_rpc_notif_port-number;
      description
        "Destination port.";
    }
    leaf url {
      type oc-inet:ncs_rpc_notif_url;
      description
        "Target URL to probe.";
    }
  }

  grouping ncs_rpc_notif_probe-test-config-base {
    description
      "Definition of test details.";
    leaf test-type {
      type oc-probes-types:ncs_rpc_notif_test-type;
      description
        "The type of the probe test.";
      mandatory true;
    }
    leaf count {
      type yang:counter64;
      description
        "The number of probes per test.";
    }
    leaf interval {
      type yang:counter64;
      description
        "Time between two consecutive probes.";
    }
    leaf source {
      type oc-inet:ncs_rpc_notif_ip-address;
      description
        "Source address used when probing, either IPv4 or IPv6.";
    }
    leaf history-size {
      type yang:counter64;
      description
        "The number of history entries stored.";
    }
    leaf source-port {
      type oc-inet:ncs_rpc_notif_port-number;
      description
        "Source number used.";
    }
    leaf dscp {
      type oc-inet:ncs_rpc_notif_dscp;
      description
        "DSCP code points";
    }
  }

  grouping ncs_rpc_notif_probe-test-state-history-item-base {
    description
      "The test item results counters and statistics.
       An item presents the results of a single execution
       of the test.
       The results of the test depend on the values
       of the total items, or an average over a certain
       period of time.";
    leaf id {
      type yang:counter64;
      description
        "The test item ID.";
    }
    leaf timestamp {
      type oc-types:ncs_rpc_notif_timeticks64;
      description
        "The test timestamp.
         This is not the timestamp when the test
         was actually executed nither when it finished.
         Should be the timestamp when the test has been scheduled.
         It may not be the same with start-timestamp.";
    }
    leaf start-timestamp {
      type oc-types:ncs_rpc_notif_timeticks64;
      description
        "The timestamp when the test started.";
    }
    leaf end-timestamp {
      type oc-types:ncs_rpc_notif_timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:ncs_rpc_notif_percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping ncs_rpc_notif_probe-test-state-history-item {
    description
      "A history item of the probe results.";
    container state {
      config false;
      description
        "A history item of the probe results: operational data only.";
      uses ncs_rpc_notif_probe-test-state-history-item-base;
    }
  }

  grouping ncs_rpc_notif_probe-test-state-history {
    description
      "The history of the test results.";
    container items {
      description
        "The list of items in the probe history.
         The length depends on the history size.";
      list item {
        key "id";
        description
          "List of history items.";
        leaf id {
          type leafref {
            path "../state/id";
          }
          description
            "Reference to the history entry ID.";
        }
        uses ncs_rpc_notif_probe-test-state-history-item;
      }
    }
  }

  grouping ncs_rpc_notif_probe-test-state-results {
    description
      "The test results counters and statistics.";
    leaf timestamp {
      type oc-types:ncs_rpc_notif_timeticks64;
      description
        "The test timestamp.
         This is not the timestamp when the test
         was actually executed nither when it finished.
         Should be the timestamp when the test has been scheduled.
         It may not be the same with start-timestamp.";
    }
    leaf start-timestamp {
      type oc-types:ncs_rpc_notif_timeticks64;
      description
        "The timestamp when the test started.";
    }
    leaf last-test-timestamp {
      type oc-types:ncs_rpc_notif_timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:ncs_rpc_notif_percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping ncs_rpc_notif_probe-test-state {
    description
      "Operational data and results for the probes.";
  }

  grouping ncs_rpc_notif_probe-test-config {
    description
      "Definition of test details.";
    leaf name {
      type string;
      description
        "The name of the test probe";
      mandatory true;
    }
    leaf enabled {
      type boolean;
      default "true";
      description
        "Whether the test is enabled.";
    }
    uses ncs_rpc_notif_probe-test-config-base;
  }

  grouping ncs_rpc_notif_probe-tests-top {
    description
      "Top-level grouping for the tests withing a probe.";
    list test {
      key "name";
      description
        "List of tests associated with this probe.";
      leaf name {
        type leafref {
          path "../config/name";
        }
        description
          "Reference to the list key";
      }
      container config {
        description
          "Configuration data for the test of this probe.";
        uses ncs_rpc_notif_probe-test-config;
      }
      container state {
        config false;
        description
          "Operational state data";
        uses ncs_rpc_notif_probe-test-config;
        uses ncs_rpc_notif_probe-test-state;
      }
      uses ncs_rpc_notif_test-target;
      container results {
        description
          "Contains the results of the tests.";
        container state {
          config false;
          description
            "Results of this test: operational data only";
          uses ncs_rpc_notif_probe-test-state-results;
        }
        container history {
          config false;
          description
            "Historical data of the tests.";
          uses ncs_rpc_notif_probe-test-state-history;
        }
      }
    }
  }

  grouping ncs_rpc_notif_probe-config {
    description
      "Definition of probe details.";
    leaf name {
      type string;
      description
        "The name of the probe.";
      mandatory true;
    }
    leaf enabled {
      type boolean;
      default "true";
      description
        "Whether the probe is enabled.";
    }
  }

  grouping ncs_rpc_notif_probe-state {
    description
      "Definition of probes operation data.";
  }

  grouping ncs_rpc_notif_probes-top {
    description
      "Top-level grouping for probes model";
    list probe {
      key "name";
      description
        "List of probes configured.";
      leaf name {
        type leafref {
          path "../config/name";
        }
        description
          "Reference to the list key";
      }
      container config {
        description
          "Configuration data for the probes.";
        uses ncs_rpc_notif_probe-config;
      }
      container state {
        config false;
        description
          "Operational state data";
        uses ncs_rpc_notif_probe-config;
        uses ncs_rpc_notif_probe-state;
      }
      container tests {
        description
          "The tests associated to be executed for the probe.";
        uses ncs_rpc_notif_probe-tests-top;
      }
    }
  }

  grouping ncs_rpc_notif_openconfig-probes-top {
    description
      "The top level grouping of the probes model.";
    container probes {
      description
        "The container containing the list of probes.";
      uses ncs_rpc_notif_probes-top;
    }
  }

  grouping live_ncs_test-target {
    description
      "Groups the config and state containers
       for an individual test.";
    container target {
      description
        "The target configuration of the test.
         The nature of the target depends on the probe type:
         for HTTP probes we need to provide an URL to poll,
         while ICMP probes require an IP address to monitor.";
      container config {
        description
          "Configuration data for the test target.";
        uses live_ncs_test-target-base;
      }
      container state {
        description
          "Operational data for the test target.";
        uses live_ncs_test-target-base;
      }
    }
  }

  grouping live_ncs_test-target-base {
    description
      "Targe types for the probe test.";
    leaf address {
      type oc-inet:live_ncs_ip-address;
      description
        "IP address of the target, either IPv4 or IPv6.";
    }
    leaf port {
      type oc-inet:live_ncs_port-number;
      description
        "Destination port.";
    }
    leaf url {
      type oc-inet:live_ncs_url;
      description
        "Target URL to probe.";
    }
  }

  grouping live_ncs_probe-test-config-base {
    description
      "Definition of test details.";
    leaf test-type {
      type oc-probes-types:live_ncs_test-type;
      description
        "The type of the probe test.";
      // NCS drop mandatory statement
    }
    leaf count {
      type yang:counter64;
      description
        "The number of probes per test.";
    }
    leaf interval {
      type yang:counter64;
      description
        "Time between two consecutive probes.";
    }
    leaf source {
      type oc-inet:live_ncs_ip-address;
      description
        "Source address used when probing, either IPv4 or IPv6.";
    }
    leaf history-size {
      type yang:counter64;
      description
        "The number of history entries stored.";
    }
    leaf source-port {
      type oc-inet:live_ncs_port-number;
      description
        "Source number used.";
    }
    leaf dscp {
      type oc-inet:live_ncs_dscp;
      description
        "DSCP code points";
    }
  }

  grouping live_ncs_probe-test-state-history-item-base {
    description
      "The test item results counters and statistics.
       An item presents the results of a single execution
       of the test.
       The results of the test depend on the values
       of the total items, or an average over a certain
       period of time.";
    leaf id {
      type yang:counter64;
      description
        "The test item ID.";
    }
    leaf timestamp {
      type oc-types:live_ncs_timeticks64;
      description
        "The test timestamp.
         This is not the timestamp when the test
         was actually executed nither when it finished.
         Should be the timestamp when the test has been scheduled.
         It may not be the same with start-timestamp.";
    }
    leaf start-timestamp {
      type oc-types:live_ncs_timeticks64;
      description
        "The timestamp when the test started.";
    }
    leaf end-timestamp {
      type oc-types:live_ncs_timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:live_ncs_percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping live_ncs_probe-test-state-history-item {
    description
      "A history item of the probe results.";
    container state {
      description
        "A history item of the probe results: operational data only.";
      uses live_ncs_probe-test-state-history-item-base;
    }
  }

  grouping live_ncs_probe-test-state-history {
    description
      "The history of the test results.";
    container items {
      description
        "The list of items in the probe history.
         The length depends on the history size.";
      list item {
        key "id";
        description
          "List of history items.";
        leaf id {
          type leafref {
            path "../state/id";
          }
          description
            "Reference to the history entry ID.";
        }
        uses live_ncs_probe-test-state-history-item;
      }
    }
  }

  grouping live_ncs_probe-test-state-results {
    description
      "The test results counters and statistics.";
    leaf timestamp {
      type oc-types:live_ncs_timeticks64;
      description
        "The test timestamp.
         This is not the timestamp when the test
         was actually executed nither when it finished.
         Should be the timestamp when the test has been scheduled.
         It may not be the same with start-timestamp.";
    }
    leaf start-timestamp {
      type oc-types:live_ncs_timeticks64;
      description
        "The timestamp when the test started.";
    }
    leaf last-test-timestamp {
      type oc-types:live_ncs_timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:live_ncs_percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping live_ncs_probe-test-state {
    description
      "Operational data and results for the probes.";
  }

  grouping live_ncs_probe-test-config {
    description
      "Definition of test details.";
    leaf name {
      type string;
      description
        "The name of the test probe";
      // NCS drop mandatory statement
    }
    leaf enabled {
      type boolean;
      // NCS drop default statement
      description
        "Whether the test is enabled.";
    }
    uses live_ncs_probe-test-config-base;
  }

  grouping live_ncs_probe-tests-top {
    description
      "Top-level grouping for the tests withing a probe.";
    list test {
      key "name";
      description
        "List of tests associated with this probe.";
      leaf name {
        type leafref {
          path "../config/name";
        }
        description
          "Reference to the list key";
      }
      container config {
        description
          "Configuration data for the test of this probe.";
        uses live_ncs_probe-test-config;
      }
      container state {
        description
          "Operational state data";
        uses live_ncs_probe-test-config;
        uses live_ncs_probe-test-state;
      }
      uses live_ncs_test-target;
      container results {
        description
          "Contains the results of the tests.";
        container state {
          description
            "Results of this test: operational data only";
          uses live_ncs_probe-test-state-results;
        }
        container history {
          description
            "Historical data of the tests.";
          uses live_ncs_probe-test-state-history;
        }
      }
    }
  }

  grouping live_ncs_probe-config {
    description
      "Definition of probe details.";
    leaf name {
      type string;
      description
        "The name of the probe.";
      // NCS drop mandatory statement
    }
    leaf enabled {
      type boolean;
      // NCS drop default statement
      description
        "Whether the probe is enabled.";
    }
  }

  grouping live_ncs_probe-state {
    description
      "Definition of probes operation data.";
  }

  grouping live_ncs_probes-top {
    description
      "Top-level grouping for probes model";
    list probe {
      key "name";
      description
        "List of probes configured.";
      leaf name {
        type leafref {
          path "../config/name";
        }
        description
          "Reference to the list key";
      }
      container config {
        description
          "Configuration data for the probes.";
        uses live_ncs_probe-config;
      }
      container state {
        description
          "Operational state data";
        uses live_ncs_probe-config;
        uses live_ncs_probe-state;
      }
      container tests {
        description
          "The tests associated to be executed for the probe.";
        uses live_ncs_probe-tests-top;
      }
    }
  }

  grouping live_ncs_openconfig-probes-top {
    description
      "The top level grouping of the probes model.";
    container probes {
      description
        "The container containing the list of probes.";
      uses live_ncs_probes-top;
    }
  }

  grouping test-target {
    description
      "Groups the config and state containers
       for an individual test.";
    container target {
      description
        "The target configuration of the test.
         The nature of the target depends on the probe type:
         for HTTP probes we need to provide an URL to poll,
         while ICMP probes require an IP address to monitor.";
      container config {
        description
          "Configuration data for the test target.";
        uses test-target-base;
      }
      // NCS drop config false container state
    }
  }

  grouping test-target-base {
    description
      "Targe types for the probe test.";
    leaf address {
      type oc-inet:ip-address;
      description
        "IP address of the target, either IPv4 or IPv6.";
    }
    leaf port {
      type oc-inet:port-number;
      description
        "Destination port.";
    }
    leaf url {
      type oc-inet:url;
      description
        "Target URL to probe.";
    }
  }

  grouping probe-test-config-base {
    description
      "Definition of test details.";
    leaf test-type {
      type oc-probes-types:test-type;
      description
        "The type of the probe test.";
      mandatory true;
    }
    leaf count {
      type yang:counter64;
      description
        "The number of probes per test.";
    }
    leaf interval {
      type yang:counter64;
      description
        "Time between two consecutive probes.";
    }
    leaf source {
      type oc-inet:ip-address;
      description
        "Source address used when probing, either IPv4 or IPv6.";
    }
    leaf history-size {
      type yang:counter64;
      description
        "The number of history entries stored.";
    }
    leaf source-port {
      type oc-inet:port-number;
      description
        "Source number used.";
    }
    leaf dscp {
      type oc-inet:dscp;
      description
        "DSCP code points";
    }
  }

  grouping probe-test-state-history-item-base {
    description
      "The test item results counters and statistics.
       An item presents the results of a single execution
       of the test.
       The results of the test depend on the values
       of the total items, or an average over a certain
       period of time.";
    leaf id {
      type yang:counter64;
      description
        "The test item ID.";
    }
    leaf timestamp {
      type oc-types:timeticks64;
      description
        "The test timestamp.
         This is not the timestamp when the test
         was actually executed nither when it finished.
         Should be the timestamp when the test has been scheduled.
         It may not be the same with start-timestamp.";
    }
    leaf start-timestamp {
      type oc-types:timeticks64;
      description
        "The timestamp when the test started.";
    }
    leaf end-timestamp {
      type oc-types:timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping probe-test-state-history-item {
    description
      "A history item of the probe results.";
    // NCS drop config false container state
  }

  grouping probe-test-state-history {
    description
      "The history of the test results.";
    container items {
      description
        "The list of items in the probe history.
         The length depends on the history size.";
      list item {
        key "id";
        description
          "List of history items.";
        leaf id {
          type leafref {
            path "../state/id";
          }
          description
            "Reference to the history entry ID.";
        }
        uses probe-test-state-history-item;
      }
    }
  }

  grouping probe-test-state-results {
    description
      "The test results counters and statistics.";
    leaf timestamp {
      type oc-types:timeticks64;
      description
        "The test timestamp.
         This is not the timestamp when the test
         was actually executed nither when it finished.
         Should be the timestamp when the test has been scheduled.
         It may not be the same with start-timestamp.";
    }
    leaf start-timestamp {
      type oc-types:timeticks64;
      description
        "The timestamp when the test started.";
    }
    leaf last-test-timestamp {
      type oc-types:timeticks64;
      description
        "The timestamp when the test finished.";
    }
    leaf test-duration {
      type yang:counter64;
      description
        "The duration of the test, in microseconds.";
    }
    leaf failed {
      type boolean;
      description
        "Whether the test failed or succeeded.";
    }
    leaf probes-sent {
      type yang:counter64;
      description
        "Number of test probes sent.";
    }
    leaf probes-received {
      type yang:counter64;
      description
        "Number of test probes received.";
    }
    leaf loss-percentage {
      type oc-types:percentage;
      description
        "The loss percentage.";
    }
    leaf jitter {
      type yang:counter64;
      description
        "The round trip jitter, in microseconds.";
    }
    leaf min-delay {
      type yang:counter64;
      description
        "The minimum delay recorded during the test, in microseconds.";
    }
    leaf max-delay {
      type yang:counter64;
      description
        "The maximum delay recorded during the test, in microseconds.";
    }
    leaf avg-delay {
      type yang:counter64;
      description
        "The average delay recorded during the test, in microseconds.";
    }
    leaf stddev-delay {
      type yang:counter64;
      description
        "The standard deviation of the delay of the test.";
    }
  }

  grouping probe-test-state {
    description
      "Operational data and results for the probes.";
  }

  grouping probe-test-config {
    description
      "Definition of test details.";
    leaf name {
      type string;
      description
        "The name of the test probe";
      mandatory true;
    }
    leaf enabled {
      type boolean;
      default "true";
      description
        "Whether the test is enabled.";
    }
    uses probe-test-config-base;
  }

  grouping probe-tests-top {
    description
      "Top-level grouping for the tests withing a probe.";
    list test {
      key "name";
      description
        "List of tests associated with this probe.";
      leaf name {
        type leafref {
          path "../config/name";
        }
        description
          "Reference to the list key";
      }
      container config {
        description
          "Configuration data for the test of this probe.";
        uses probe-test-config;
      }
      // NCS drop config false container state
      uses test-target;
      container results {
        description
          "Contains the results of the tests.";
        // NCS drop config false container state
        // NCS drop config false container history
      }
    }
  }

  grouping probe-config {
    description
      "Definition of probe details.";
    leaf name {
      type string;
      description
        "The name of the probe.";
      mandatory true;
    }
    leaf enabled {
      type boolean;
      default "true";
      description
        "Whether the probe is enabled.";
    }
  }

  grouping probe-state {
    description
      "Definition of probes operation data.";
  }

  grouping probes-top {
    description
      "Top-level grouping for probes model";
    list probe {
      key "name";
      description
        "List of probes configured.";
      leaf name {
        type leafref {
          path "../config/name";
        }
        description
          "Reference to the list key";
      }
      container config {
        description
          "Configuration data for the probes.";
        uses probe-config;
      }
      // NCS drop config false container state
      container tests {
        description
          "The tests associated to be executed for the probe.";
        uses probe-tests-top;
      }
    }
  }

  grouping openconfig-probes-top {
    description
      "The top level grouping of the probes model.";
    container probes {
      description
        "The container containing the list of probes.";
      uses probes-top;
    }
  }

  augment "/ncs:devices/ncs:device/ncs:config" {
    uses openconfig-probes-top {
      refine probes {
        tailf:ncs-device-type "netconf";
        tailf:display-when "not(../../ncs:module) or ../../ncs:module[ncs:name='openconfig-probes']";
      }
    }
  }
  augment "/ncs:devices/ncs:device/ncs:live-status" {
    uses live_ncs_openconfig-probes-top {
      refine probes {
        tailf:ncs-device-type "netconf";
        tailf:display-when "not(../../ncs:module) or ../../ncs:module[ncs:name='openconfig-probes'] or (../../ncs:live-status-protocol[not(ncs:capability)]) or (../../ncs:live-status-protocol/ncs:capability/ncs:module[.='openconfig-probes'])";
      }
    }
  }
  augment "/ncs:devices/ncs:template/ncs:ned-id/ncs:config" {
    uses ncs_template_openconfig-probes-top;
  }
}
