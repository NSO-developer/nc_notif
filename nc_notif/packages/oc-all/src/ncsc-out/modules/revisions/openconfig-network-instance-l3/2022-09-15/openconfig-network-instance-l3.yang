module openconfig-network-instance-l3 {
  // Generated by yanger -t ncs
  tailf:mount-id "oc-all-nc-1.0:oc-all-nc-1.0";
  tailf:ncs-device-type "netconf";

  yang-version 1;
  namespace "http://openconfig.net/yang/network-instance-l3";
  prefix oc-ni-l3;

  import openconfig-extensions {
    prefix oc-ext;
  }
  import openconfig-types {
    prefix octypes;
  }
  import tailf-common {
    prefix tailf;
  }
  import tailf-ncs {
    prefix ncs;
  }

  organization
    "OpenConfig working group";
  contact
    "OpenConfig working group
     www.openconfig.net";
  description
    "This module contains groupings which specifically relate to
     Layer 3 network instance configuration and operational state
     parameters.";
  oc-ext:openconfig-version "1.0.0";

  revision 2022-09-15 {
    description
      "Reflect implementation status by releasing 1.0.0.";
    reference "1.0.0";
  }
  revision 2018-11-21 {
    description
      "Add OpenConfig module metadata extensions.";
    reference "0.11.1";
  }
  revision 2018-08-17 {
    description
      "Add a route limit for L3 network instances.";
    reference "0.11.0";
  }
  revision 2017-12-13 {
    description
      "Fix incorrect constraint on SR and MPLS containers";
    reference "0.9.0";
  }
  revision 2017-08-24 {
    description
      "Minor formatting fixes";
    reference "0.8.1";
  }
  revision 2017-02-28 {
    description
      "Add OSPFv2 to network instance";
    reference "0.8.0";
  }
  revision 2017-01-26 {
    description
      "Add policy forwarding to network instance";
    reference "0.7.0";
  }
  revision 2017-01-13 {
    description
      "Add AFT to the network instance";
    reference "0.6.0";
  }
  revision 2016-12-15 {
    description
      "Add segment routing to network instance";
    reference "0.5.0";
  }
  revision 2016-11-10 {
    description
      "Update model to include IS-IS.";
    reference "0.4.1";
  }
  revision 2016-09-28 {
    description
      "Change L2 instance to submodule; add MAC table";
    reference "0.3.0";
  }
  revision 2016-08-11 {
    description
      "Resolve repeated container names in routing protocols";
    reference "0.2.3";
  }
  revision 2016-07-08 {
    description
      "Updated with refactored routing protocol models";
    reference "0.2.1";
  }
  revision 2016-03-29 {
    description
      "Initial revision";
    reference "0.2.0";
  }
  revision 2016-03-14 {
    description
      "Initial revision";
    reference "0.1.0";
  }
  oc-ext:regexp-posix;
  oc-ext:catalog-organization "openconfig";
  oc-ext:origin "openconfig";

  grouping ncs_template_l3ni-instance {
    description
      "Configuration and operational state parameters relevant
       to network instances that include a Layer 3 type";
  }

  grouping ncs_template_l3ni-instance-common-config {
    description
      "Configuration parameters that are common to L3 network
       instances other than the default instance";
    leaf-list enabled-address-families {
      // NCS patched for predictable order
      ordered-by user;
      type string;
      description
        "The address families that are to be enabled for this
         network instance.";
    }
  }

  grouping ncs_template_l3ni-route-limit-structural {
    description
      "Configuration and state for the maximum number of routes
       that should be used by routing instance.";
    container route-limits {
      description
        "Configuration and operational state relating to the
         maximum number of routes for the address family that
         should be allowed within the Layer 3 network instance.

         When the specified value is reached, no further prefixes
         should be installed into the system's RIB from this network
         instance unless the warning only leaf is set. In this case,
         new routes should still be installed. If a alarm threshold
         is specified, then this should be used to generate
         alarms via telemetry for the network instance.";
      list route-limit {
        // NCS patched for predictable order
        ordered-by user;
        key "afi";
        description
          "A route limit applying to a particular address family.";
        leaf afi {
          type string;
          description
            "Reference to the address family for which the route
             limit is being applied.";
        }
        container config {
          description
            "Configuration options relating to the route limit.";
          uses ncs_template_l3ni-route-limit-config;
        }
        // NCS drop config false container state
      }
    }
  }

  grouping ncs_template_l3ni-route-limit-config {
    description
      "Configuration options relating to the route limit for a network
       instance.";
    leaf afi {
      type string;
      description
        "The address family for which the route limit applies.";
    }
    leaf maximum {
      type string;
      description
        "The maximum number of routes for the address family. The
         system should not install more than maximum number of
         prefixes into the RIB unless the warning-only leaf is specified.";
    }
    leaf warning-only {
      type string;
      // NCS drop default statement
      description
        "When specified, the route limit specified is considered only as
         a warning - and routes should continue to be installed into the
         RIB over the limit specified in the maximum leaf.";
    }
    leaf alarm-threshold {
      type string;
      description
        "When specified, an alarm should be generated when the threshold
         number of installed routes is reached.";
    }
  }

  grouping ncs_template_l3ni-route-limit-state {
    description
      "Operational state relating to the route limit for a network
       instance.";
    leaf threshold-exceeded {
      type string;
      description
        "This leaf should be set to true in the case that the threshold
         number of routes has been exceeded.";
    }
    leaf installed-routes {
      type string;
      description
        "The current number of routes installed for the address family.";
    }
  }

  grouping ncs_rpc_notif_l3ni-instance {
    description
      "Configuration and operational state parameters relevant
       to network instances that include a Layer 3 type";
  }

  grouping ncs_rpc_notif_l3ni-instance-common-config {
    description
      "Configuration parameters that are common to L3 network
       instances other than the default instance";
    leaf-list enabled-address-families {
      type identityref {
        base octypes:ADDRESS_FAMILY;
      }
      description
        "The address families that are to be enabled for this
         network instance.";
    }
  }

  grouping ncs_rpc_notif_l3ni-route-limit-structural {
    description
      "Configuration and state for the maximum number of routes
       that should be used by routing instance.";
    container route-limits {
      description
        "Configuration and operational state relating to the
         maximum number of routes for the address family that
         should be allowed within the Layer 3 network instance.

         When the specified value is reached, no further prefixes
         should be installed into the system's RIB from this network
         instance unless the warning only leaf is set. In this case,
         new routes should still be installed. If a alarm threshold
         is specified, then this should be used to generate
         alarms via telemetry for the network instance.";
      list route-limit {
        key "afi";
        description
          "A route limit applying to a particular address family.";
        leaf afi {
          type leafref {
            path "../config/afi";
          }
          description
            "Reference to the address family for which the route
             limit is being applied.";
        }
        container config {
          description
            "Configuration options relating to the route limit.";
          uses ncs_rpc_notif_l3ni-route-limit-config;
        }
        container state {
          config false;
          description
            "Operational state parameters relating to the route limit.";
          uses ncs_rpc_notif_l3ni-route-limit-config;
          uses ncs_rpc_notif_l3ni-route-limit-state;
        }
      }
    }
  }

  grouping ncs_rpc_notif_l3ni-route-limit-config {
    description
      "Configuration options relating to the route limit for a network
       instance.";
    leaf afi {
      type identityref {
        base octypes:ADDRESS_FAMILY;
      }
      description
        "The address family for which the route limit applies.";
    }
    leaf maximum {
      type uint32;
      description
        "The maximum number of routes for the address family. The
         system should not install more than maximum number of
         prefixes into the RIB unless the warning-only leaf is specified.";
    }
    leaf warning-only {
      type boolean;
      default "false";
      description
        "When specified, the route limit specified is considered only as
         a warning - and routes should continue to be installed into the
         RIB over the limit specified in the maximum leaf.";
    }
    leaf alarm-threshold {
      type uint32;
      description
        "When specified, an alarm should be generated when the threshold
         number of installed routes is reached.";
    }
  }

  grouping ncs_rpc_notif_l3ni-route-limit-state {
    description
      "Operational state relating to the route limit for a network
       instance.";
    leaf threshold-exceeded {
      type boolean;
      description
        "This leaf should be set to true in the case that the threshold
         number of routes has been exceeded.";
    }
    leaf installed-routes {
      type uint32;
      description
        "The current number of routes installed for the address family.";
    }
  }

  grouping live_ncs_l3ni-instance {
    description
      "Configuration and operational state parameters relevant
       to network instances that include a Layer 3 type";
  }

  grouping live_ncs_l3ni-instance-common-config {
    description
      "Configuration parameters that are common to L3 network
       instances other than the default instance";
    leaf-list enabled-address-families {
      type identityref {
        base octypes:ADDRESS_FAMILY;
      }
      description
        "The address families that are to be enabled for this
         network instance.";
    }
  }

  grouping live_ncs_l3ni-route-limit-structural {
    description
      "Configuration and state for the maximum number of routes
       that should be used by routing instance.";
    container route-limits {
      description
        "Configuration and operational state relating to the
         maximum number of routes for the address family that
         should be allowed within the Layer 3 network instance.

         When the specified value is reached, no further prefixes
         should be installed into the system's RIB from this network
         instance unless the warning only leaf is set. In this case,
         new routes should still be installed. If a alarm threshold
         is specified, then this should be used to generate
         alarms via telemetry for the network instance.";
      list route-limit {
        key "afi";
        description
          "A route limit applying to a particular address family.";
        leaf afi {
          type leafref {
            path "../config/afi";
          }
          description
            "Reference to the address family for which the route
             limit is being applied.";
        }
        container config {
          description
            "Configuration options relating to the route limit.";
          uses live_ncs_l3ni-route-limit-config;
        }
        container state {
          description
            "Operational state parameters relating to the route limit.";
          uses live_ncs_l3ni-route-limit-config;
          uses live_ncs_l3ni-route-limit-state;
        }
      }
    }
  }

  grouping live_ncs_l3ni-route-limit-config {
    description
      "Configuration options relating to the route limit for a network
       instance.";
    leaf afi {
      type identityref {
        base octypes:ADDRESS_FAMILY;
      }
      description
        "The address family for which the route limit applies.";
    }
    leaf maximum {
      type uint32;
      description
        "The maximum number of routes for the address family. The
         system should not install more than maximum number of
         prefixes into the RIB unless the warning-only leaf is specified.";
    }
    leaf warning-only {
      type boolean;
      // NCS drop default statement
      description
        "When specified, the route limit specified is considered only as
         a warning - and routes should continue to be installed into the
         RIB over the limit specified in the maximum leaf.";
    }
    leaf alarm-threshold {
      type uint32;
      description
        "When specified, an alarm should be generated when the threshold
         number of installed routes is reached.";
    }
  }

  grouping live_ncs_l3ni-route-limit-state {
    description
      "Operational state relating to the route limit for a network
       instance.";
    leaf threshold-exceeded {
      type boolean;
      description
        "This leaf should be set to true in the case that the threshold
         number of routes has been exceeded.";
    }
    leaf installed-routes {
      type uint32;
      description
        "The current number of routes installed for the address family.";
    }
  }

  grouping l3ni-instance {
    description
      "Configuration and operational state parameters relevant
       to network instances that include a Layer 3 type";
  }

  grouping l3ni-instance-common-config {
    description
      "Configuration parameters that are common to L3 network
       instances other than the default instance";
    leaf-list enabled-address-families {
      type identityref {
        base octypes:ADDRESS_FAMILY;
      }
      description
        "The address families that are to be enabled for this
         network instance.";
    }
  }

  grouping l3ni-route-limit-structural {
    description
      "Configuration and state for the maximum number of routes
       that should be used by routing instance.";
    container route-limits {
      description
        "Configuration and operational state relating to the
         maximum number of routes for the address family that
         should be allowed within the Layer 3 network instance.

         When the specified value is reached, no further prefixes
         should be installed into the system's RIB from this network
         instance unless the warning only leaf is set. In this case,
         new routes should still be installed. If a alarm threshold
         is specified, then this should be used to generate
         alarms via telemetry for the network instance.";
      list route-limit {
        key "afi";
        description
          "A route limit applying to a particular address family.";
        leaf afi {
          type leafref {
            path "../config/afi";
          }
          description
            "Reference to the address family for which the route
             limit is being applied.";
        }
        container config {
          description
            "Configuration options relating to the route limit.";
          uses l3ni-route-limit-config;
        }
        // NCS drop config false container state
      }
    }
  }

  grouping l3ni-route-limit-config {
    description
      "Configuration options relating to the route limit for a network
       instance.";
    leaf afi {
      type identityref {
        base octypes:ADDRESS_FAMILY;
      }
      description
        "The address family for which the route limit applies.";
    }
    leaf maximum {
      type uint32;
      description
        "The maximum number of routes for the address family. The
         system should not install more than maximum number of
         prefixes into the RIB unless the warning-only leaf is specified.";
    }
    leaf warning-only {
      type boolean;
      default "false";
      description
        "When specified, the route limit specified is considered only as
         a warning - and routes should continue to be installed into the
         RIB over the limit specified in the maximum leaf.";
    }
    leaf alarm-threshold {
      type uint32;
      description
        "When specified, an alarm should be generated when the threshold
         number of installed routes is reached.";
    }
  }

  grouping l3ni-route-limit-state {
    description
      "Operational state relating to the route limit for a network
       instance.";
    leaf threshold-exceeded {
      type boolean;
      description
        "This leaf should be set to true in the case that the threshold
         number of routes has been exceeded.";
    }
    leaf installed-routes {
      type uint32;
      description
        "The current number of routes installed for the address family.";
    }
  }
}
