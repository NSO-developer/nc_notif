module openconfig-platform-fan {
  // Generated by yanger -t ncs
  tailf:mount-id "oc-all-nc-1.0:oc-all-nc-1.0";
  tailf:ncs-device-type "netconf";

  yang-version 1;
  namespace "http://openconfig.net/yang/platform/fan";
  prefix oc-fan;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines data related to FAN components in the
     OpenConfig platform model.";
  oc-ext:openconfig-version "0.1.1";

  revision 2018-11-21 {
    description
      "Add OpenConfig module metadata extensions.";
    reference "0.1.1";
  }
  revision 2018-01-18 {
    description
      "Initial revision";
    reference "0.1.0";
  }
  oc-ext:regexp-posix;
  oc-ext:catalog-organization "openconfig";
  oc-ext:origin "openconfig";

  grouping ncs_template_fan-state {
    description
      "Operational state data for fan components";
    leaf speed {
      type string;
      units "rpm";
      description
        "Current (instantaneous) fan speed";
    }
  }

  grouping ncs_rpc_notif_fan-state {
    description
      "Operational state data for fan components";
    leaf speed {
      type uint32;
      units "rpm";
      description
        "Current (instantaneous) fan speed";
    }
  }

  grouping live_ncs_fan-state {
    description
      "Operational state data for fan components";
    leaf speed {
      type uint32;
      units "rpm";
      description
        "Current (instantaneous) fan speed";
    }
  }

  grouping fan-state {
    description
      "Operational state data for fan components";
    leaf speed {
      type uint32;
      units "rpm";
      description
        "Current (instantaneous) fan speed";
    }
  }

  augment "/ncs:devices/ncs:device/ncs:live-status/oc-platform:components/oc-platform:component/oc-platform:fan/oc-platform:state" {
    description
      "Adding fan data to component model";
    uses live_ncs_fan-state {
      refine speed {
        tailf:ncs-device-type "netconf";
        tailf:display-when "not(../../../../../../ncs:module) or ../../../../../../ncs:module[ncs:name='openconfig-platform-fan'] or (../../../../../../ncs:live-status-protocol[not(ncs:capability)]) or (../../../../../../ncs:live-status-protocol/ncs:capability/ncs:module[.='openconfig-platform-fan'])";
      }
    }
  }
}
